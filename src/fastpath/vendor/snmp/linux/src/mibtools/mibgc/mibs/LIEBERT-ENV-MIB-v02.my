--
-- Version 4.1.0 - goes with Liebert's 4.1.0 agent 
--
LIEBERT-ENV-MIB-v02 DEFINITIONS ::= BEGIN

IMPORTS
    MODULE-IDENTITY, OBJECT-TYPE, 
    enterprises, Counter32, Integer32
        FROM SNMPv2-SMI
    DisplayString, TruthValue FROM SNMPv2-TC
    MODULE-COMPLIANCE, OBJECT-GROUP
        FROM SNMPv2-CONF;

--        IMPORTS
--          enterprises, Counter,
--          DisplayString               FROM RFC1155-SMI
--          OBJECT-TYPE                 FROM RFC-1212;


--
-- Emerson Enterprises branch
--
        emerson OBJECT IDENTIFIER ::= { enterprises 476 }

--
-- Divisions of Emerson
--
        liebertCorp OBJECT IDENTIFIER ::= { emerson 1 }


--
-- Areas of Liebert Corporation
--

        liebertUps OBJECT IDENTIFIER ::= { liebertCorp 1 }
        liebertEnvironment OBJECT IDENTIFIER ::= { liebertCorp 2 }

--
-- Environment Area
--
        leExtensions OBJECT IDENTIFIER ::= { liebertEnvironment 1 }

        leExperimental OBJECT IDENTIFIER ::= { liebertEnvironment 2 }

        lePrivate OBJECT IDENTIFIER ::= { liebertEnvironment 3 }

        leSiteNet01 OBJECT IDENTIFIER ::= { leExtensions 1 }
  

envMIB MODULE-IDENTITY
        LAST-UPDATED  "94030400000Z"
        ORGANIZATION  "Liebert"
        CONTACT-INFO
		"	
			SNMP Research, Inc

		Postal:		 
			3001 Kimberlin Heights Rd.
			Knoxville, TN  37920-9716
			US

		   Tel: +1 615 573-1434
		   Fax: +1 615 573-9197

		E-mail: support@snmp.com"
	
        DESCRIPTION
		"This MIB is used to manage Environmental Control
		products of Liebert.  Version 0.3"

::= { leSiteNet01 1 }



--
-- Environmental MIB version 1.1
--
--        envMIB OBJECT IDENTIFIER ::= {leSiteNet01 1 }
--

--
-- Environmental Products MIB Version Number
--

-- NOTE: these OID's are embedeed in the envMIB OBJECT IDENTIFIER
--      envMIBVersion1  OBJECT IDENTIFIER ::= { leExtensions 1 }
--      envMIBV03       OBJECT IDENTIFIER ::= { envMIBVersion1 1 }

--
-- Environmental Extensions
--

        --
        -- The Device Identification group.
        --      All objects in this group are determined at device
        --      initialization and remain static.
        --

        envIdent OBJECT IDENTIFIER ::= { envMIB 1 }

        envIdentManufacturer OBJECT-TYPE
            SYNTAX DisplayString (SIZE (64))
            MAX-ACCESS read-only
            STATUS current
            DESCRIPTION
                "The Environmental Control Unit manufacturer."
            ::= { envIdent 1 }

        envIdentModel OBJECT-TYPE
            SYNTAX DisplayString (SIZE (64))
            MAX-ACCESS read-write
            STATUS current
            DESCRIPTION
                "The Environmental Control Unit Model designation."
            ::= { envIdent 2 }

        envIdentSoftwareVersion OBJECT-TYPE
            SYNTAX DisplayString (SIZE (64))
            MAX-ACCESS read-only
            STATUS current
            DESCRIPTION
                "The Environmental SNMP Agent software version."
            ::= { envIdent 3 }


        envIdentSpecific OBJECT-TYPE
            SYNTAX OBJECT IDENTIFIER
            MAX-ACCESS read-only
            STATUS current
            DESCRIPTION
                "A reference to MIB definitions specific to the
                particular Environmental Unit being managed. This
                object is used to locate the product-specific MIB
                 for this device.

                If this information is not present, its value
                should be the OBJECT IDENTIFIER { 0 0 },
                which is a syntactically valid object identifier,
                and any conformant implementation of ASN.1 and BER
                must be able to generate and recognize this
                value."
            ::= { envIdent 4 }


--
-- Digital Inputs
--

        envDigitalInputs OBJECT IDENTIFIER ::= { envMIB 2 }

--
-- Digital Input 1
--

        envDigInput1 OBJECT IDENTIFIER ::= { envDigitalInputs 1 }

        envDigInput1State OBJECT-TYPE
            SYNTAX INTEGER { true(1), false(2), notInstalled(3) }
            MAX-ACCESS read-only
            STATUS current
            DESCRIPTION
                "The state of Digital Input Number 1.

                When the envDigInput1Polarity is set to notDefined(3)
                this variable returns notInstalled(3).  When the
                envDigInput1Polarity is set to activeHigh(1) and the
                input on Digital Input Number 1 is asserted, this
                variable returns true(1).  When the envDigInput1Polarity
                is set to activeLow(2) and the input on Digital Input 1
                is deasserted, this variable returns true(1).  In all
                other cases, this variable returns false(2)."
        ::= { envDigInput1 1 }

        envDigInput1Label OBJECT-TYPE
            SYNTAX DisplayString (SIZE (64))
            MAX-ACCESS read-write
            STATUS current
            DESCRIPTION
                "A user-defined text string associated with
                Digital Input Number 1.  The text string is stored
                in non-volatile memory."
        ::= { envDigInput1 2 }


        envDigInput1Polarity OBJECT-TYPE
            SYNTAX INTEGER { activeHigh(1), activeLow(2), notDefined(3) }
            MAX-ACCESS read-write
            STATUS current
            DESCRIPTION
                "The Polarity to be associated with the State variable for
                Digital Input Number 1.  It controls the value returned by
                the State variable.

                When Polarity is set to notDefined(3), State will return
                notInstalled(3).  When Polarity is set to activeHigh(1),
                State will return false(2) if Digital Input Number 1 is
                being deasserted and return true(1) if Digital Input
                Number 1 is being asserted.  When Polarity is set to
                activeHigh(1), State will return false(2) if Digital Input
                Number 1 is being asserted and return true(1) if Digital
                Input Number 1 is being deasserted.  Polarity is stored
                in non-volatile memory."
        ::= { envDigInput1 3 }

        envDigInput1TrapEnabled OBJECT-TYPE
            SYNTAX TruthValue
            MAX-ACCESS read-write
            STATUS current
            DESCRIPTION
                "A TRAP may be associated with the State variable for
                Digital Input Number 1.

                When envDigInput1TrapEnabled is set to true(1), a TRAP
                message will be generated when State is true(1).  When
                envDigInput1TrapEnabled is set to false(2), a TRAP message
                will not be generated regardless of the value of State.
                TrapEnabled is stored in non-volatile memory."
        ::= { envDigInput1 4 }

--
-- These next two objects are only used by the Sitenet Desktop Agent.
--

	envDigInp1TrueTrapEnabled OBJECT-TYPE
    	    SYNTAX  TruthValue
    	    MAX-ACCESS  read-write
    	    STATUS  current
    	    DESCRIPTION
           	"A TRAP may be associated with the true(1) value for the
		State variable for Digital Input Number 1.

                When envDigInp1TrueTrapEnabled is set to true(1) a TRAP
                message will be generated when State becomes true(1).
		When envDigInp1TrueTrapEnabled is set to false(2) a TRAP
		message will not be generated when State becomes true(1).
		TrapEnabled is stored in non-volatile memory."
    	::= { envDigInput1  5 }

	envDigInp1FalseTrapEnabled OBJECT-TYPE
    	    SYNTAX  TruthValue
    	    MAX-ACCESS  read-write
    	    STATUS  current
    	    DESCRIPTION
                "A TRAP may be associated with the false(2) value for the
		State variable for Digital Input Number 1.

                When envDigInp1FalseTrapEnabled is set to true(1) a TRAP
                message will be generated when State becomes false(2).
		When envDigInp1FalseTrapEnabled is set to false(2) a
		TRAP message will not be generated when State becomes
		false(2).  TrapEnabled is stored in non-volatile memory."
    	::= { envDigInput1  6 }

--
-- Digital Input 2
--
        envDigInput2 OBJECT IDENTIFIER ::= { envDigitalInputs 2 }

        envDigInput2State OBJECT-TYPE
            SYNTAX INTEGER { true(1), false(2), notInstalled(3) }
            MAX-ACCESS read-only
            STATUS current
            DESCRIPTION
                "The state of Digital Input Number 2.

                When the envDigInput2Polarity is set to notDefined(3)
                this variable returns notInstalled(3).  When the
                envDigInput2Polarity is set to activeHigh(1) and the
                input on Digital Input Number 2 is asserted, this
                variable returns true(1).  When the envDigInput2Polarity
                is set to activeLow(2) and the input on Digital Input 2
                is deasserted, this variable returns true(1).  In all
                other cases, this variable returns false(2)."
        ::= { envDigInput2 1 }

        envDigInput2Label OBJECT-TYPE
            SYNTAX DisplayString (SIZE (64))
            MAX-ACCESS read-write
            STATUS current
            DESCRIPTION
                "A user-defined text string associated with
                Digital Input Number 2.  The text string is stored
                in non-volatile memory."
        ::= { envDigInput2 2 }


        envDigInput2Polarity OBJECT-TYPE
            SYNTAX INTEGER { activeHigh(1), activeLow(2), notDefined(3) }
            MAX-ACCESS read-write
            STATUS current
            DESCRIPTION
                "The Polarity to be associated with the State variable for
                Digital Input Number 2.  It controls the value returned by
                the State variable.

                When Polarity is set to notDefined(3), State will return
                notInstalled(3).  When Polarity is set to activeHigh(1),
                State will return false(2) if Digital Input Number 2 is
                being deasserted and return true(1) if Digital Input
                Number 2 is being asserted.  When Polarity is set to
                activeHigh(1), State will return false(2) if Digital Input
                Number 2 is being asserted and return true(1) if Digital
                Input Number 2 is being deasserted.  Polarity is stored
                in non-volatile memory."
        ::= { envDigInput2 3 }

        envDigInput2TrapEnabled OBJECT-TYPE
            SYNTAX TruthValue
            MAX-ACCESS read-write
            STATUS current
            DESCRIPTION
                "A TRAP may be associated with the State variable for
                Digital Input Number 2.

                When envDigInput2TrapEnabled is set to true(1), a TRAP
                message will be generated when State is true(1).  When
                envDigInput2TrapEnabled is set to false(2), a TRAP message
                will not be generated regardless of the value of State.
                TrapEnabled is stored in non-volatile memory."
        ::= { envDigInput2 4 }

--
-- These next two objects are only used by the Sitenet Desktop Agent.
--

	envDigInp2TrueTrapEnabled OBJECT-TYPE
    	    SYNTAX  TruthValue
    	    MAX-ACCESS  read-write
    	    STATUS  current
    	    DESCRIPTION
           	"A TRAP may be associated with the true(1) value for the
		State variable for Digital Input Number 2.

                When envDigInp2TrueTrapEnabled is set to true(1) a TRAP
                message will be generated when State becomes true(1).
		When envDigInp2TrueTrapEnabled is set to false(2) a TRAP
		message will not be generated when State becomes true(1).
		TrapEnabled is stored in non-volatile memory."
    	::= { envDigInput2  5 }

	envDigInp2FalseTrapEnabled OBJECT-TYPE
    	    SYNTAX  TruthValue
    	    MAX-ACCESS  read-write
    	    STATUS  current
    	    DESCRIPTION
           	"A TRAP may be associated with the false(2) value for the
		State variable for Digital Input Number 2.

                When envDigInp2FalseTrapEnabled is set to true(1) a TRAP
                message will be generated when State becomes false(2).
		When envDigInp2FalseTrapEnabled is set to false(2) a
		TRAP message will not be generated when State becomes
		false(2).  TrapEnabled is stored in non-volatile memory."
    	::= { envDigInput2  6 }

--
-- Digital Input 3
--
        envDigInput3 OBJECT IDENTIFIER ::= { envDigitalInputs 3 }

        envDigInput3State OBJECT-TYPE
            SYNTAX INTEGER { true(1), false(2), notInstalled(3) }
            MAX-ACCESS read-only
            STATUS current
            DESCRIPTION
                "The state of Digital Input Number 3.

                When the envDigInput3Polarity is set to notDefined(3)
                this variable returns notInstalled(3).  When the
                envDigInput3Polarity is set to activeHigh(1) and the
                input on Digital Input Number 3 is asserted, this
                variable returns true(1).  When the envDigInput3Polarity
                is set to activeLow(2) and the input on Digital Input 3
                is deasserted, this variable returns true(1).  In all
                other cases, this variable returns false(2)."
        ::= { envDigInput3 1 }

        envDigInput3Label OBJECT-TYPE
            SYNTAX DisplayString (SIZE (64))
            MAX-ACCESS read-write
            STATUS current
            DESCRIPTION
                "A user-defined text string associated with
                Digital Input Number 3.  The text string is stored
                in non-volatile memory."
        ::= { envDigInput3 2 }


        envDigInput3Polarity OBJECT-TYPE
            SYNTAX INTEGER { activeHigh(1), activeLow(2), notDefined(3) }
            MAX-ACCESS read-write
            STATUS current
            DESCRIPTION
                "The Polarity to be associated with the State variable for
                Digital Input Number 3.  It controls the value returned by
                the State variable.

                When Polarity is set to notDefined(3), State will return
                notInstalled(3).  When Polarity is set to activeHigh(1),
                State will return false(2) if Digital Input Number 3 is
                being deasserted and return true(1) if Digital Input
                Number 3 is being asserted.  When Polarity is set to
                activeHigh(1), State will return false(2) if Digital Input
                Number 3 is being asserted and return true(1) if Digital
                Input Number 3 is being deasserted.  Polarity is stored
                in non-volatile memory."
        ::= { envDigInput3 3 }

        envDigInput3TrapEnabled OBJECT-TYPE
            SYNTAX TruthValue
            MAX-ACCESS read-write
            STATUS current
            DESCRIPTION
                "A TRAP may be associated with the State variable for
                Digital Input Number 3.

                When envDigInput3TrapEnabled is set to true(1), a TRAP
                message will be generated when State is true(1).  When
                envDigInput3TrapEnabled is set to false(2), a TRAP message
                will not be generated regardless of the value of State.
                TrapEnabled is stored in non-volatile memory."
        ::= { envDigInput3 4 }

--
-- Digital Input 4
--
        envDigInput4 OBJECT IDENTIFIER ::= { envDigitalInputs 4 }

        envDigInput4State OBJECT-TYPE
            SYNTAX INTEGER { true(1), false(2), notInstalled(3) }
            MAX-ACCESS read-only
            STATUS current
            DESCRIPTION
                "The state of Digital Input Number 4.

                When the envDigInput4Polarity is set to notDefined(3)
                this variable returns notInstalled(3).  When the
                envDigInput4Polarity is set to activeHigh(1) and the
                input on Digital Input Number 4 is asserted, this
                variable returns true(1).  When the envDigInput4Polarity
                is set to activeLow(2) and the input on Digital Input 4
                is deasserted, this variable returns true(1).  In all
                other cases, this variable returns false(2)."
        ::= { envDigInput4 1 }

        envDigInput4Label OBJECT-TYPE
            SYNTAX DisplayString (SIZE (64))
            MAX-ACCESS read-write
            STATUS current
            DESCRIPTION
                "A user-defined text string associated with
                Digital Input Number 4.  The text string is stored
                in non-volatile memory."
        ::= { envDigInput4 2 }


        envDigInput4Polarity OBJECT-TYPE
            SYNTAX INTEGER { activeHigh(1), activeLow(2), notDefined(3) }
            MAX-ACCESS read-write
            STATUS current
            DESCRIPTION
                "The Polarity to be associated with the State variable for
                Digital Input Number 4.  It controls the value returned by
                the State variable.

                When Polarity is set to notDefined(3), State will return
                notInstalled(3).  When Polarity is set to activeHigh(1),
                State will return false(2) if Digital Input Number 4 is
                being deasserted and return true(1) if Digital Input
                Number 4 is being asserted.  When Polarity is set to
                activeHigh(1), State will return false(2) if Digital Input
                Number 4 is being asserted and return true(1) if Digital
                Input Number 4 is being deasserted.  Polarity is stored
                in non-volatile memory."
        ::= { envDigInput4 3 }

        envDigInput4TrapEnabled OBJECT-TYPE
            SYNTAX TruthValue
            MAX-ACCESS read-write
            STATUS current
            DESCRIPTION
                "A TRAP may be associated with the State variable for
                Digital Input Number 4.

                When envDigInput4TrapEnabled is set to true(1), a TRAP
                message will be generated when State is true(1).  When
                envDigInput4TrapEnabled is set to false(2), a TRAP message
                will not be generated regardless of the value of State.
                TrapEnabled is stored in non-volatile memory."
        ::= { envDigInput4 4 }

--
-- Digital Input 5
--
        envDigInput5 OBJECT IDENTIFIER ::= { envDigitalInputs 5 }

        envDigInput5State OBJECT-TYPE
            SYNTAX INTEGER { true(1), false(2), notInstalled(3) }
            MAX-ACCESS read-only
            STATUS current
            DESCRIPTION
                "The state of Digital Input Number 5.

                When the envDigInput5Polarity is set to notDefined(3)
                this variable returns notInstalled(3).  When the
                envDigInput5Polarity is set to activeHigh(1) and the
                input on Digital Input Number 5 is asserted, this
                variable returns true(1).  When the envDigInput5Polarity
                is set to activeLow(2) and the input on Digital Input 5
                is deasserted, this variable returns true(1).  In all
                other cases, this variable returns false(2)."
        ::= { envDigInput5 1 }

        envDigInput5Label OBJECT-TYPE
            SYNTAX DisplayString (SIZE (64))
            MAX-ACCESS read-write
            STATUS current
            DESCRIPTION
                "A user-defined text string associated with
                Digital Input Number 5.  The text string is stored
                in non-volatile memory."
        ::= { envDigInput5 2 }


        envDigInput5Polarity OBJECT-TYPE
            SYNTAX INTEGER { activeHigh(1), activeLow(2), notDefined(3) }
            MAX-ACCESS read-write
            STATUS current
            DESCRIPTION
                "The Polarity to be associated with the State variable for
                Digital Input Number 5.  It controls the value returned by
                the State variable.

                When Polarity is set to notDefined(3), State will return
                notInstalled(3).  When Polarity is set to activeHigh(1),
                State will return false(2) if Digital Input Number 5 is
                being deasserted and return true(1) if Digital Input
                Number 5 is being asserted.  When Polarity is set to
                activeHigh(1), State will return false(2) if Digital Input
                Number 5 is being asserted and return true(1) if Digital
                Input Number 5 is being deasserted.  Polarity is stored
                in non-volatile memory."
        ::= { envDigInput5 3 }

        envDigInput5TrapEnabled OBJECT-TYPE
            SYNTAX TruthValue
            MAX-ACCESS read-write
            STATUS current
            DESCRIPTION
                "A TRAP may be associated with the State variable for
                Digital Input Number 5.

                When envDigInput5TrapEnabled is set to true(1), a TRAP
                message will be generated when State is true(1).  When
                envDigInput5TrapEnabled is set to false(2), a TRAP message
                will not be generated regardless of the value of State.
                TrapEnabled is stored in non-volatile memory."
        ::= { envDigInput5 4 }

--
-- Digital Input 6
--
        envDigInput6 OBJECT IDENTIFIER ::= { envDigitalInputs 6 }

        envDigInput6State OBJECT-TYPE
            SYNTAX INTEGER { true(1), false(2), notInstalled(3) }
            MAX-ACCESS read-only
            STATUS current
            DESCRIPTION
                "The state of Digital Input Number 6.

                When the envDigInput6Polarity is set to notDefined(3)
                this variable returns notInstalled(3).  When the
                envDigInput6Polarity is set to activeHigh(1) and the
                input on Digital Input Number 6 is asserted, this
                variable returns true(1).  When the envDigInput6Polarity
                is set to activeLow(2) and the input on Digital Input 6
                is deasserted, this variable returns true(1).  In all
                other cases, this variable returns false(2)."
        ::= { envDigInput6 1 }

        envDigInput6Label OBJECT-TYPE
            SYNTAX DisplayString (SIZE (64))
            MAX-ACCESS read-write
            STATUS current
            DESCRIPTION
                "A user-defined text string associated with
                Digital Input Number 6.  The text string is stored
                in non-volatile memory."
        ::= { envDigInput6 2 }


        envDigInput6Polarity OBJECT-TYPE
            SYNTAX INTEGER { activeHigh(1), activeLow(2), notDefined(3) }
            MAX-ACCESS read-write
            STATUS current
            DESCRIPTION
                "The Polarity to be associated with the State variable for
                Digital Input Number 6.  It controls the value returned by
                the State variable.

                When Polarity is set to notDefined(3), State will return
                notInstalled(3).  When Polarity is set to activeHigh(1),
                State will return false(2) if Digital Input Number 6 is
                being deasserted and return true(1) if Digital Input
                Number 6 is being asserted.  When Polarity is set to
                activeHigh(1), State will return false(2) if Digital Input
                Number 6 is being asserted and return true(1) if Digital
                Input Number 6 is being deasserted.  Polarity is stored
                in non-volatile memory."
        ::= { envDigInput6 3 }

        envDigInput6TrapEnabled OBJECT-TYPE
            SYNTAX TruthValue
            MAX-ACCESS read-write
            STATUS current
            DESCRIPTION
                "A TRAP may be associated with the State variable for
                Digital Input Number 6.

                When envDigInput6TrapEnabled is set to true(1), a TRAP
                message will be generated when State is true(1).  When
                envDigInput6TrapEnabled is set to false(2), a TRAP message
                will not be generated regardless of the value of State.
                TrapEnabled is stored in non-volatile memory."
        ::= { envDigInput6 4 }

--
-- Digital Input 7
--
        envDigInput7 OBJECT IDENTIFIER ::= { envDigitalInputs 7 }

        envDigInput7State OBJECT-TYPE
            SYNTAX INTEGER { true(1), false(2), notInstalled(3) }
            MAX-ACCESS read-only
            STATUS current
            DESCRIPTION
                "The state of Digital Input Number 7.

                When the envDigInput7Polarity is set to notDefined(3)
                this variable returns notInstalled(3).  When the
                envDigInput7Polarity is set to activeHigh(1) and the
                input on Digital Input Number 7 is asserted, this
                variable returns true(1).  When the envDigInput7Polarity
                is set to activeLow(2) and the input on Digital Input 7
                is deasserted, this variable returns true(1).  In all
                other cases, this variable returns false(2)."
        ::= { envDigInput7 1 }

        envDigInput7Label OBJECT-TYPE
            SYNTAX DisplayString (SIZE (64))
            MAX-ACCESS read-write
            STATUS current
            DESCRIPTION
                "A user-defined text string associated with
                Digital Input Number 7.  The text string is stored
                in non-volatile memory."
        ::= { envDigInput7 2 }


        envDigInput7Polarity OBJECT-TYPE
            SYNTAX INTEGER { activeHigh(1), activeLow(2), notDefined(3) }
            MAX-ACCESS read-write
            STATUS current
            DESCRIPTION
                "The Polarity to be associated with the State variable for
                Digital Input Number 7.  It controls the value returned by
                the State variable.

                When Polarity is set to notDefined(3), State will return
                notInstalled(3).  When Polarity is set to activeHigh(1),
                State will return false(2) if Digital Input Number 7 is
                being deasserted and return true(1) if Digital Input
                Number 7 is being asserted.  When Polarity is set to
                activeHigh(1), State will return false(2) if Digital Input
                Number 7 is being asserted and return true(1) if Digital
                Input Number 7 is being deasserted.  Polarity is stored
                in non-volatile memory."
        ::= { envDigInput7 3 }

        envDigInput7TrapEnabled OBJECT-TYPE
            SYNTAX TruthValue
            MAX-ACCESS read-write
            STATUS current
            DESCRIPTION
                "A TRAP may be associated with the State variable for
                Digital Input Number 7.

                When envDigInput7TrapEnabled is set to true(1), a TRAP
                message will be generated when State is true(1).  When
                envDigInput7TrapEnabled is set to false(2), a TRAP message
                will not be generated regardless of the value of State.
                TrapEnabled is stored in non-volatile memory."
        ::= { envDigInput7 4 }

--
-- Digital Input 8
--
        envDigInput8 OBJECT IDENTIFIER ::= { envDigitalInputs 8 }

        envDigInput8State OBJECT-TYPE
            SYNTAX INTEGER { true(1), false(2), notInstalled(3) }
            MAX-ACCESS read-only
            STATUS current
            DESCRIPTION
                "The state of Digital Input Number 8.

                When the envDigInput8Polarity is set to notDefined(3)
                this variable returns notInstalled(3).  When the
                envDigInput8Polarity is set to activeHigh(1) and the
                input on Digital Input Number 8 is asserted, this
                variable returns true(1).  When the envDigInput8Polarity
                is set to activeLow(2) and the input on Digital Input 8
                is deasserted, this variable returns true(1).  In all
                other cases, this variable returns false(2)."
        ::= { envDigInput8 1 }

        envDigInput8Label OBJECT-TYPE
            SYNTAX DisplayString (SIZE (64))
            MAX-ACCESS read-write
            STATUS current
            DESCRIPTION
                "A user-defined text string associated with
                Digital Input Number 8.  The text string is stored
                in non-volatile memory."
        ::= { envDigInput8 2 }


        envDigInput8Polarity OBJECT-TYPE
            SYNTAX INTEGER { activeHigh(1), activeLow(2), notDefined(3) }
            MAX-ACCESS read-write
            STATUS current
            DESCRIPTION
                "The Polarity to be associated with the State variable for
                Digital Input Number 8.  It controls the value returned by
                the State variable.

                When Polarity is set to notDefined(3), State will return
                notInstalled(3).  When Polarity is set to activeHigh(1),
                State will return false(2) if Digital Input Number 8 is
                being deasserted and return true(1) if Digital Input
                Number 8 is being asserted.  When Polarity is set to
                activeHigh(1), State will return false(2) if Digital Input
                Number 8 is being asserted and return true(1) if Digital
                Input Number 8 is being deasserted.  Polarity is stored
                in non-volatile memory."
        ::= { envDigInput8 3 }

        envDigInput8TrapEnabled OBJECT-TYPE
            SYNTAX TruthValue
            MAX-ACCESS read-write
            STATUS current
            DESCRIPTION
                "A TRAP may be associated with the State variable for
                Digital Input Number 8.

                When envDigInput8TrapEnabled is set to true(1), a TRAP
                message will be generated when State is true(1).  When
                envDigInput8TrapEnabled is set to false(2), a TRAP message
                will not be generated regardless of the value of State.
                TrapEnabled is stored in non-volatile memory."
        ::= { envDigInput8 4 }

--
-- Digital Input 9
--
        envDigInput9 OBJECT IDENTIFIER ::= { envDigitalInputs 9 }

        envDigInput9State OBJECT-TYPE
            SYNTAX INTEGER { true(1), false(2), notInstalled(3) }
            MAX-ACCESS read-only
            STATUS current
            DESCRIPTION
                "The state of Digital Input Number 9.

                When the envDigInput9Polarity is set to notDefined(3)
                this variable returns notInstalled(3).  When the
                envDigInput9Polarity is set to activeHigh(1) and the
                input on Digital Input Number 9 is asserted, this
                variable returns true(1).  When the envDigInput9Polarity
                is set to activeLow(2) and the input on Digital Input 9
                is deasserted, this variable returns true(1).  In all
                other cases, this variable returns false(2)."
        ::= { envDigInput9 1 }

        envDigInput9Label OBJECT-TYPE
            SYNTAX DisplayString (SIZE (64))
            MAX-ACCESS read-write
            STATUS current
            DESCRIPTION
                "A user-defined text string associated with
                Digital Input Number 9.  The text string is stored
                in non-volatile memory."
        ::= { envDigInput9 2 }


        envDigInput9Polarity OBJECT-TYPE
            SYNTAX INTEGER { activeHigh(1), activeLow(2), notDefined(3) }
            MAX-ACCESS read-write
            STATUS current
            DESCRIPTION
                "The Polarity to be associated with the State variable for
                Digital Input Number 9.  It controls the value returned by
                the State variable.

                When Polarity is set to notDefined(3), State will return
                notInstalled(3).  When Polarity is set to activeHigh(1),
                State will return false(2) if Digital Input Number 9 is
                being deasserted and return true(1) if Digital Input
                Number 9 is being asserted.  When Polarity is set to
                activeHigh(1), State will return false(2) if Digital Input
                Number 9 is being asserted and return true(1) if Digital
                Input Number 9 is being deasserted.  Polarity is stored
                in non-volatile memory."
        ::= { envDigInput9 3 }

        envDigInput9TrapEnabled OBJECT-TYPE
            SYNTAX TruthValue
            MAX-ACCESS read-write
            STATUS current
            DESCRIPTION
                "A TRAP may be associated with the State variable for
                Digital Input Number 9.

                When envDigInput9TrapEnabled is set to true(1), a TRAP
                message will be generated when State is true(1).  When
                envDigInput9TrapEnabled is set to false(2), a TRAP message
                will not be generated regardless of the value of State.
                TrapEnabled is stored in non-volatile memory."
        ::= { envDigInput9 4 }

--
-- Digital Input 10
--
        envDigInput10 OBJECT IDENTIFIER ::= { envDigitalInputs 10 }

        envDigInput10State OBJECT-TYPE
            SYNTAX INTEGER { true(1), false(2), notInstalled(3) }
            MAX-ACCESS read-only
            STATUS current
            DESCRIPTION
                "The state of Digital Input Number 10.

                When the envDigInput10Polarity is set to notDefined(3)
                this variable returns notInstalled(3).  When the
                envDigInput10Polarity is set to activeHigh(1) and the
                input on Digital Input Number 10 is asserted, this
                variable returns true(1).  When the envDigInput10Polarity
                is set to activeLow(2) and the input on Digital Input 10
                is deasserted, this variable returns true(1).  In all
                other cases, this variable returns false(2)."
        ::= { envDigInput10 1 }

        envDigInput10Label OBJECT-TYPE
            SYNTAX DisplayString (SIZE (64))
            MAX-ACCESS read-write
            STATUS current
            DESCRIPTION
                "A user-defined text string associated with
                Digital Input Number 10.  The text string is stored
                in non-volatile memory."
        ::= { envDigInput10 2 }


        envDigInput10Polarity OBJECT-TYPE
            SYNTAX INTEGER { activeHigh(1), activeLow(2), notDefined(3) }
            MAX-ACCESS read-write
            STATUS current
            DESCRIPTION
                "The Polarity to be associated with the State variable for
                Digital Input Number 10.  It controls the value returned by
                the State variable.

                When Polarity is set to notDefined(3), State will return
                notInstalled(3).  When Polarity is set to activeHigh(1),
                State will return false(2) if Digital Input Number 10 is
                being deasserted and return true(1) if Digital Input
                Number 10 is being asserted.  When Polarity is set to
                activeHigh(1), State will return false(2) if Digital Input
                Number 10 is being asserted and return true(1) if Digital
                Input Number 10 is being deasserted.  Polarity is stored
                in non-volatile memory."
        ::= { envDigInput10 3 }

        envDigInput10TrapEnabled OBJECT-TYPE
            SYNTAX TruthValue
            MAX-ACCESS read-write
            STATUS current
            DESCRIPTION
                "A TRAP may be associated with the State variable for
                Digital Input Number 10.

                When envDigInput10TrapEnabled is set to true(1), a TRAP
                message will be generated when State is true(1).  When
                envDigInput10TrapEnabled is set to false(2), a TRAP message
                will not be generated regardless of the value of State.
                TrapEnabled is stored in non-volatile memory."
        ::= { envDigInput10 4 }


--
-- Relay Outputs
--

        envRelays OBJECT IDENTIFIER ::= { envMIB 3 }

--
-- Relay Output 1
--
        envRelay1 OBJECT IDENTIFIER ::= { envRelays 1 }

        envRelay1State OBJECT-TYPE
            SYNTAX INTEGER { on(1), off(2) }
            MAX-ACCESS read-write
            STATUS current
            DESCRIPTION
                "The state of Output Relay Number 1.

                When State is set to on(1) Output Relay Number 1 is
                activated and the normally open contacts are closed.
                When State is set to off(2) Output Relay Number 1 is
                deactivated and the normally closed contacts are closed."
        ::= { envRelay1 1 }

        envRelay1Label OBJECT-TYPE
            SYNTAX DisplayString (SIZE (64))
            MAX-ACCESS read-write
            STATUS current
            DESCRIPTION
                "A user-defined text string associated with
                Output Relay Number 1.  The text string is stored
                in non-volatile memory."
        ::= { envRelay1 2 }

        envRelay1Control OBJECT-TYPE
            SYNTAX Integer32
            MAX-ACCESS read-write
            STATUS current
            DESCRIPTION
                "If Control value is 0 then this output may be directly
                controlled by the SNMP Manager.  When Control contains any
                of the following values, or a value resulting from the sum
                of any of these values the Agent will activate the output
                when the any of the associated conditions is sensed and
                de-activate the output when all conditions clear.

                DigitalInput1State true(1)      1
                DigitalInput2State true(1)      2
                DigitalInput3State true(1)      4
                DigitalInput4State true(1)      8
                DigitalInput5State true(1)      16
                DigitalInput6State true(1)      32
                DigitalInput7State true(1)      64
                DigitalInput8State true(1)      128
                DigitalInput9State true(1)      256
                DigitalInput10State true(1)     512
                Temperature1 above HighLimit    1024
                Temperature1 below LowLimit     2048
                Temperature2 above HighLimit    4096
                Temperature2 below LowLimit     8192
                Temperature3 above HighLimit    16384
                Temperature3 below LowLimit     32768
                Humidity1 above HighLimit       65536
                Humidity1 below LowLimit        131072
                Humidity2 above HighLimit       262144
                Humidity2 below LowLimit        524288

                The Control variable is stored in non-volatile memory."
        ::= { envRelay1 3 }

--
-- Relay Output 2
--
        envRelay2 OBJECT IDENTIFIER ::= { envRelays 2 }

        envRelay2State OBJECT-TYPE
            SYNTAX INTEGER { on(1), off(2) }
            MAX-ACCESS read-write
            STATUS current
            DESCRIPTION
                "The state of Output Relay Number 2.

                When State is set to on(1) Output Relay Number 2 is
                activated and the normally open contacts are closed.
                When State is set to off(2) Output Relay Number 2 is
                deactivated and the normally closed contacts are closed."
        ::= { envRelay2 1 }

        envRelay2Label OBJECT-TYPE
            SYNTAX DisplayString (SIZE (64))
            MAX-ACCESS read-write
            STATUS current
            DESCRIPTION
                "A user-defined text string associated with
                Output Relay Number 2.  The text string is stored
                in non-volatile memory."
        ::= { envRelay2 2 }

        envRelay2Control OBJECT-TYPE
            SYNTAX Integer32
            MAX-ACCESS read-write
            STATUS current
            DESCRIPTION
                "If Control value is 0 then this output may be directly
                controlled by the SNMP Manager.  When Control contains any
                of the following values, or a value resulting from the sum
                of any of these values the Agent will activate the output
                when the any of the associated conditions is sensed and
                de-activate the output when all conditions clear.

                DigitalInput1State true(1)      1
                DigitalInput2State true(1)      2
                DigitalInput3State true(1)      4
                DigitalInput4State true(1)      8
                DigitalInput5State true(1)      16
                DigitalInput6State true(1)      32
                DigitalInput7State true(1)      64
                DigitalInput8State true(1)      128
                DigitalInput9State true(1)      256
                DigitalInput10State true(1)     512
                Temperature1 above HighLimit    1024
                Temperature1 below LowLimit     2048
                Temperature2 above HighLimit    4096
                Temperature2 below LowLimit     8192
                Temperature3 above HighLimit    16384
                Temperature3 below LowLimit     32768
                Humidity1 above HighLimit       65536
                Humidity1 below LowLimit        131072
                Humidity2 above HighLimit       262144
                Humidity2 below LowLimit        524288

                The Control variable is stored in non-volatile memory."
        ::= { envRelay2 3 }


--
-- Outputs
--

        envOutputs OBJECT IDENTIFIER ::= { envMIB 4 }

--
-- Output 1
--
        envAudible OBJECT IDENTIFIER ::= { envOutputs 1 }

        envAudibleState OBJECT-TYPE
            SYNTAX INTEGER { on(1), off(2) }
            MAX-ACCESS read-write
            STATUS current
            DESCRIPTION
                "The state of the Audible Output.

                When State is set to on(1) the Audible will be sounded.
                When State is set to off(2) the Audible is muted."
        ::= { envAudible 1 }

        envAudibleControl OBJECT-TYPE
            SYNTAX Integer32
            MAX-ACCESS read-write
            STATUS current
            DESCRIPTION
                "If Control value is 0 then this output may be directly
                controlled by the SNMP Manager.  When Control contains any
                of the following values, or a value resulting from the sum
                of any of these values the Agent will activate the output
                when the any of the associated conditions is sensed and
                de-activate the output when all conditions clear.

                DigitalInput1State true(1)      1
                DigitalInput2State true(1)      2
                DigitalInput3State true(1)      4
                DigitalInput4State true(1)      8
                DigitalInput5State true(1)      16
                DigitalInput6State true(1)      32
                DigitalInput7State true(1)      64
                DigitalInput8State true(1)      128
                DigitalInput9State true(1)      256
                DigitalInput10State true(1)     512
                Temperature1 above HighLimit    1024
                Temperature1 below LowLimit     2048
                Temperature2 above HighLimit    4096
                Temperature2 below LowLimit     8192
                Temperature3 above HighLimit    16384
                Temperature3 below LowLimit     32768
                Humidity1 above HighLimit       65536
                Humidity1 below LowLimit        131072
                Humidity2 above HighLimit       262144
                Humidity2 below LowLimit        524288

                The Control variable is stored in non-volatile memory."
        ::= { envAudible 2 }

--
-- Output 2
--
        envLED1 OBJECT IDENTIFIER ::= { envOutputs 2 }

        envLED1State OBJECT-TYPE
            SYNTAX INTEGER { on(1), off(2) }
            MAX-ACCESS read-write
            STATUS current
            DESCRIPTION
                "The state of Output LED Number 1.

                When State is set to on(1) LED Number 1 will be lighted.
                When State is set to off(2) LED Number 1 will not be
                lighted."
        ::= { envLED1 1 }

        envLED1Label OBJECT-TYPE
            SYNTAX DisplayString (SIZE (64))
            MAX-ACCESS read-write
            STATUS current
            DESCRIPTION
                "A user-defined text string associated with
                Output LED Number 1.  The text string is stored
                in non-volatile memory."
        ::= { envLED1 2 }

        envLED1Control OBJECT-TYPE
            SYNTAX Integer32
            MAX-ACCESS read-write
            STATUS current
            DESCRIPTION
                "If Control value is 0 then this output may be directly
                controlled by the SNMP Manager.  When Control contains any
                of the following values, or a value resulting from the sum
                of any of these values the Agent will activate the output
                when the any of the associated conditions is sensed and
                de-activate the output when all conditions clear.

                DigitalInput1State true(1)      1
                DigitalInput2State true(1)      2
                DigitalInput3State true(1)      4
                DigitalInput4State true(1)      8
                DigitalInput5State true(1)      16
                DigitalInput6State true(1)      32
                DigitalInput7State true(1)      64
                DigitalInput8State true(1)      128
                DigitalInput9State true(1)      256
                DigitalInput10State true(1)     512
                Temperature1 above HighLimit    1024
                Temperature1 below LowLimit     2048
                Temperature2 above HighLimit    4096
                Temperature2 below LowLimit     8192
                Temperature3 above HighLimit    16384
                Temperature3 below LowLimit     32768
                Humidity1 above HighLimit       65536
                Humidity1 below LowLimit        131072
                Humidity2 above HighLimit       262144
                Humidity2 below LowLimit        524288

                The Control variable is stored in non-volatile memory."
        ::= { envLED1 3 }

--
-- Output 3
--
        envLED2 OBJECT IDENTIFIER ::= { envOutputs 3 }

        envLED2State OBJECT-TYPE
            SYNTAX INTEGER { on(1), off(2) }
            MAX-ACCESS read-write
            STATUS current
            DESCRIPTION
                "The state of Output LED Number 2.

                When State is set to on(1) LED Number 2 will be lighted.
                When State is set to off(2) LED Number 2 will not be
                lighted."
        ::= { envLED2 1 }

        envLED2Label OBJECT-TYPE
            SYNTAX DisplayString (SIZE (64))
            MAX-ACCESS read-write
            STATUS current
            DESCRIPTION
                "A user-defined text string associated with
                Output LED Number 2.  The text string is stored
                in non-volatile memory."
        ::= { envLED2 2 }

        envLED2Control OBJECT-TYPE
            SYNTAX Integer32
            MAX-ACCESS read-write
            STATUS current
            DESCRIPTION
                "If Control value is 0 then this output may be directly
                controlled by the SNMP Manager.  When Control contains any
                of the following values, or a value resulting from the sum
                of any of these values the Agent will activate the output
                when the any of the associated conditions is sensed and
                de-activate the output when all conditions clear.

                DigitalInput1State true(1)      1
                DigitalInput2State true(1)      2
                DigitalInput3State true(1)      4
                DigitalInput4State true(1)      8
                DigitalInput5State true(1)      16
                DigitalInput6State true(1)      32
                DigitalInput7State true(1)      64
                DigitalInput8State true(1)      128
                DigitalInput9State true(1)      256
                DigitalInput10State true(1)     512
                Temperature1 above HighLimit    1024
                Temperature1 below LowLimit     2048
                Temperature2 above HighLimit    4096
                Temperature2 below LowLimit     8192
                Temperature3 above HighLimit    16384
                Temperature3 below LowLimit     32768
                Humidity1 above HighLimit       65536
                Humidity1 below LowLimit        131072
                Humidity2 above HighLimit       262144
                Humidity2 below LowLimit        524288

                The Control variable is stored in non-volatile memory."
        ::= { envLED2 3 }

--
-- Output 4
--
        envLED3 OBJECT IDENTIFIER ::= { envOutputs 4 }

        envLED3State OBJECT-TYPE
            SYNTAX INTEGER { on(1), off(2) }
            MAX-ACCESS read-write
            STATUS current
            DESCRIPTION
                "The state of Output LED Number 3.

                When State is set to on(1) LED Number 3 will be lighted.
                When State is set to off(2) LED Number 3 will not be
                lighted."
        ::= { envLED3 1 }

        envLED3Label OBJECT-TYPE
            SYNTAX DisplayString (SIZE (64))
            MAX-ACCESS read-write
            STATUS current
            DESCRIPTION
                "A user-defined text string associated with
                Output LED Number 3.  The text string is stored
                in non-volatile memory."
        ::= { envLED3 2 }

        envLED3Control OBJECT-TYPE
            SYNTAX Integer32
            MAX-ACCESS read-write
            STATUS current
            DESCRIPTION
                "If Control value is 0 then this output may be directly
                controlled by the SNMP Manager.  When Control contains any
                of the following values, or a value resulting from the sum
                of any of these values the Agent will activate the output
                when the any of the associated conditions is sensed and
                de-activate the output when all conditions clear.

                DigitalInput1State true(1)      1
                DigitalInput2State true(1)      2
                DigitalInput3State true(1)      4
                DigitalInput4State true(1)      8
                DigitalInput5State true(1)      16
                DigitalInput6State true(1)      32
                DigitalInput7State true(1)      64
                DigitalInput8State true(1)      128
                DigitalInput9State true(1)      256
                DigitalInput10State true(1)     512
                Temperature1 above HighLimit    1024
                Temperature1 below LowLimit     2048
                Temperature2 above HighLimit    4096
                Temperature2 below LowLimit     8192
                Temperature3 above HighLimit    16384
                Temperature3 below LowLimit     32768
                Humidity1 above HighLimit       65536
                Humidity1 below LowLimit        131072
                Humidity2 above HighLimit       262144
                Humidity2 below LowLimit        524288

                The Control variable is stored in non-volatile memory."
        ::= { envLED3 3 }


--
-- Receptacle Outputs
--

        envReceptacles OBJECT IDENTIFIER ::= { envMIB 5 }

--
-- Receptacle Output 1
--
        envReceptacle1 OBJECT IDENTIFIER ::= { envReceptacles 1 }

        envReceptacle1State OBJECT-TYPE
            SYNTAX INTEGER { on(1), off(2) }
            MAX-ACCESS read-write
            STATUS current
            DESCRIPTION
                "The state of the Receptacle Number 1.

                When State is set to on(1) power will be live on
                Receptacle Number 1.  When State is set to off(2)
                no power is available from Receptacle Number 1."
        ::= { envReceptacle1 1 }

        envReceptacle1Label OBJECT-TYPE
            SYNTAX DisplayString (SIZE (64))
            MAX-ACCESS read-write
            STATUS current
            DESCRIPTION
                "A user-defined text string associated with
                Receptacle Number 1.  The text string is stored
                in non-volatile memory."
        ::= { envReceptacle1 2 }

--
-- Receptacle Output 2
--
        envReceptacle2 OBJECT IDENTIFIER ::= { envReceptacles 2 }

        envReceptacle2State OBJECT-TYPE
            SYNTAX INTEGER { on(1), off(2) }
            MAX-ACCESS read-write
            STATUS current
            DESCRIPTION
                "The state of the Receptacle Number 2.

                When State is set to on(1) power will be live on
                Receptacle Number 2.  When State is set to off(2)
                no power is available from Receptacle Number 2."
        ::= { envReceptacle2 1 }

        envReceptacle2Label OBJECT-TYPE
            SYNTAX DisplayString (SIZE (64))
            MAX-ACCESS read-write
            STATUS current
            DESCRIPTION
                "A user-defined text string associated with
                Receptacle Number 2.  The text string is stored
                in non-volatile memory."
        ::= { envReceptacle2 2 }

--
-- Receptacle Output 3
--
        envReceptacle3 OBJECT IDENTIFIER ::= { envReceptacles 3 }

        envReceptacle3State OBJECT-TYPE
            SYNTAX INTEGER { on(1), off(2) }
            MAX-ACCESS read-write
            STATUS current
            DESCRIPTION
                "The state of the Receptacle Number 3.

                When State is set to on(1) power will be live on
                Receptacle Number 3.  When State is set to off(2)
                no power is available from Receptacle Number 3."
        ::= { envReceptacle3 1 }

        envReceptacle3Label OBJECT-TYPE
            SYNTAX DisplayString (SIZE (64))
            MAX-ACCESS read-write
            STATUS current
            DESCRIPTION
                "A user-defined text string associated with
                Receptacle Number 3.  The text string is stored
                in non-volatile memory."
        ::= { envReceptacle3 2 }

--
-- Receptacle Output 4
--
        envReceptacle4 OBJECT IDENTIFIER ::= { envReceptacles 4 }

        envReceptacle4State OBJECT-TYPE
            SYNTAX INTEGER { on(1), off(2) }
            MAX-ACCESS read-write
            STATUS current
            DESCRIPTION
                "The state of the Receptacle Number 4.

                When State is set to on(1) power will be live on
                Receptacle Number 4.  When State is set to off(2)
                no power is available from Receptacle Number 4."
        ::= { envReceptacle4 1 }

        envReceptacle4Label OBJECT-TYPE
            SYNTAX DisplayString (SIZE (64))
            MAX-ACCESS read-write
            STATUS current
            DESCRIPTION
                "A user-defined text string associated with
                Receptacle Number 4.  The text string is stored
                in non-volatile memory."
        ::= { envReceptacle4 2 }


--
-- Summary Alarm
--
        envAlarms OBJECT IDENTIFIER ::= { envMIB 6 }

        envSummaryAlarm OBJECT-TYPE
            SYNTAX Integer32
            MAX-ACCESS read-only
            STATUS current
            DESCRIPTION
                "The envSummaryAlarm varible will be 0 when no
                Digital Inputs are true and no other alarm conditions
                exist.

                When alarms are active or Digital Inputs are true the
                value of envSummaryAlarm indicates which alarms and
                inputs are active as a sum of the values listed below:

                DigitalInput1State true(1)      1
                DigitalInput2State true(1)      2
                DigitalInput3State true(1)      4
                DigitalInput4State true(1)      8
                DigitalInput5State true(1)      16
                DigitalInput6State true(1)      32
                DigitalInput7State true(1)      64
                DigitalInput8State true(1)      128
                DigitalInput9State true(1)      256
                DigitalInput10State true(1)     512
                Temperature1 above HighLimit    1024
                Temperature1 below LowLimit     2048
                Temperature2 above HighLimit    4096
                Temperature2 below LowLimit     8192
                Temperature3 above HighLimit    16384
                Temperature3 below LowLimit     32768
                Humidity1 above HighLimit       65536
                Humidity1 below LowLimit        131072
                Humidity2 above HighLimit       262144
                Humidity2 below LowLimit        524288"
        ::= { envAlarms 1 }


--
-- Temperature Sensor Inputs
--
        envTemperatureSensors OBJECT IDENTIFIER ::= { envMIB 7 }

--
-- Temperature Input 1
--

        envTemperature1 OBJECT IDENTIFIER
        ::= { envTemperatureSensors 1 }

        envTemperature1State OBJECT-TYPE
            SYNTAX INTEGER { notInstalled(1), installed(2) }
            MAX-ACCESS read-write
            STATUS current
            DESCRIPTION
                "The state of use of Temperature Input Number 1.

                When a sensor is connected to Temperature Input 1
                set State to installed(2) to indicate that the value
                of envTemperature1F and envTemperature1C are valid.
                When no sensor is connected to Temperature Input 1 set
                State to notInstalled(1) to indicate that the value of
                envTemperature1F and envTemperature1C may not be valid.

		This variable is stored in non-volatile memory."
        ::= { envTemperature1 1 }

        envTemperature1F  OBJECT-TYPE
            SYNTAX Integer32
            MAX-ACCESS read-only
            STATUS current
            DESCRIPTION
                "The temperature for sensor 1 in degrees
                Fahrenheit."
        ::= { envTemperature1 2 }

        envTemperature1C  OBJECT-TYPE
            SYNTAX Integer32
            MAX-ACCESS read-only
            STATUS current
            DESCRIPTION
                "The temperature for sensor 1 in degrees
                Centigrade."
        ::= { envTemperature1 3 }

        envTemperature1Label OBJECT-TYPE
            SYNTAX DisplayString (SIZE (64))
            MAX-ACCESS read-write
            STATUS current
            DESCRIPTION
                "A user-defined text string associated with
                Temperature Input Number 1.  The text string is
                stored in non-volatile memory."
        ::= { envTemperature1 4 }

        envTemperature1OffsetF OBJECT-TYPE
            SYNTAX Integer32
            MAX-ACCESS read-write
            STATUS current
            DESCRIPTION
                "A temperature correction Offset associated with
                the envTemperature1F variable.

                The value of OffsetF is added to the value from
                Temperature Sensor Number 1 to obtain the value of
                the envTemperature1F variable.  When this variable is
                changed the envTemperature1OffsetC variable may also
                be effected.  The OffsetF variable is stored in
                non-volatile memory."
        ::= { envTemperature1 5 }

        envTemperature1OffsetC OBJECT-TYPE
            SYNTAX Integer32
            MAX-ACCESS read-write
            STATUS current
            DESCRIPTION
                "A temperature correction Offset associated with
                the envTemperature1C variable.

                The value of OffsetC is added to the value from
                Temperature Sensor Number 1 to obtain the value of
                the envTemperature1C variable.  When this variable is
                changed the envTemperature1OffsetF variable may also
                be effected.  The OffsetC variable is stored in
                in non-volatile memory."
        ::= { envTemperature1 6 }

        envTemp1HighLimitF OBJECT-TYPE
            SYNTAX Integer32
            MAX-ACCESS read-write
            STATUS current
            DESCRIPTION
                "When envTemperature1F reaches or exceeds this value
                a trap will be generated signifying a high temperature
                condition at temperature sensor 1.  The HighLimitF
                variable is stored in non-volatile memory."
        ::= { envTemperature1 7 }

        envTemp1HighLimitC OBJECT-TYPE
            SYNTAX Integer32
            MAX-ACCESS read-write
            STATUS current
            DESCRIPTION
                "When envTemperature1C reaches or exceeds this value
                a trap will be generated signifying a high temperature
                condition at temperature sensor 1.  The HighLimitC
                variable is stored in non-volatile memory."
        ::= { envTemperature1 8 }

        envTemp1LowLimitF OBJECT-TYPE
            SYNTAX Integer32
            MAX-ACCESS read-write
            STATUS current
            DESCRIPTION
                "When envTemperature1F reaches or goes below this value
                a trap will be generated signifying a low temperature
                condition at temperature sensor 1.  The LowLimitF
                variable is stored in non-volatile memory."
        ::= { envTemperature1 9 }

        envTemp1LowLimitC OBJECT-TYPE
            SYNTAX Integer32
            MAX-ACCESS read-write
            STATUS current
            DESCRIPTION
                "When envTemperature1C reaches or goes below this value
                a trap will be generated signifying a low temperature
                condition at temperature sensor 1.  The LowLimitC
                variable is stored in non-volatile memory."
        ::= { envTemperature1 10 }

--
-- Temperature Input 2
--

        envTemperature2 OBJECT IDENTIFIER
        ::= { envTemperatureSensors 2 }

        envTemperature2State OBJECT-TYPE
            SYNTAX INTEGER { notInstalled(1), installed(2) }
            MAX-ACCESS read-write
            STATUS current
            DESCRIPTION
                "The state of use of Temperature Input Number 2.

                When a sensor is connected to Temperature Input 2
                set State to installed(2) to indicate that the value
                of envTemperature2F and envTemperature2C are valid.
                When no sensor is connected to Temperature Input 2 set
                State to notInstalled(1) to indicate that the value of
                envTemperature2F and envTemperature2C may not be valid.

		This variable is stored in non-volatile memory."
        ::= { envTemperature2 1 }

        envTemperature2F  OBJECT-TYPE
            SYNTAX Integer32
            MAX-ACCESS read-only
            STATUS current
            DESCRIPTION
                "The temperature for sensor 2 in degrees
                Fahrenheit."
        ::= { envTemperature2 2 }

        envTemperature2C  OBJECT-TYPE
            SYNTAX Integer32
            MAX-ACCESS read-only
            STATUS current
            DESCRIPTION
                "The temperature for sensor 2 in degrees
                Centigrade."
        ::= { envTemperature2 3 }

        envTemperature2Label OBJECT-TYPE
            SYNTAX DisplayString (SIZE (64))
            MAX-ACCESS read-write
            STATUS current
            DESCRIPTION
                "A user-defined text string associated with
                Temperature Input Number 2.  The text string is
                stored in non-volatile memory."
        ::= { envTemperature2 4 }

        envTemperature2OffsetF OBJECT-TYPE
            SYNTAX Integer32
            MAX-ACCESS read-write
            STATUS current
            DESCRIPTION
                "A temperature correction Offset associated with
                the envTemperature2F variable.

                The value of OffsetF is added to the value from
                Temperature Sensor Number 2 to obtain the value of
                the envTemperature2F variable.  When this variable is
                changed the envTemperature2OffsetC variable may also
                be effected.  The OffsetF variable is stored in
                non-volatile memory."
        ::= { envTemperature2 5 }

        envTemperature2OffsetC OBJECT-TYPE
            SYNTAX Integer32
            MAX-ACCESS read-write
            STATUS current
            DESCRIPTION
                "A temperature correction Offset associated with
                the envTemperature2C variable.

                The value of OffsetC is added to the value from
                Temperature Sensor Number 2 to obtain the value of
                the envTemperature2C variable.  When this variable is
                changed the envTemperature2OffsetF variable may also
                be effected.  The OffsetC variable is stored in
                in non-volatile memory."
        ::= { envTemperature2 6 }

        envTemp2HighLimitF OBJECT-TYPE
            SYNTAX Integer32
            MAX-ACCESS read-write
            STATUS current
            DESCRIPTION
                "When envTemperature2F reaches or exceeds this value
                a trap will be generated signifying a high temperature
                condition at temperature sensor 2.  The HighLimitF
                variable is stored in non-volatile memory."
        ::= { envTemperature2 7 }

        envTemp2HighLimitC OBJECT-TYPE
            SYNTAX Integer32
            MAX-ACCESS read-write
            STATUS current
            DESCRIPTION
                "When envTemperature2C reaches or exceeds this value
                a trap will be generated signifying a high temperature
                condition at temperature sensor 2.  The HighLimitC
                variable is stored in non-volatile memory."
        ::= { envTemperature2 8 }

        envTemp2LowLimitF OBJECT-TYPE
            SYNTAX Integer32
            MAX-ACCESS read-write
            STATUS current
            DESCRIPTION
                "When envTemperature2F reaches or goes below this value
                a trap will be generated signifying a low temperature
                condition at temperature sensor 2.  The LowLimitF
                variable is stored in non-volatile memory."
        ::= { envTemperature2 9 }

        envTemp2LowLimitC OBJECT-TYPE
            SYNTAX Integer32
            MAX-ACCESS read-write
            STATUS current
            DESCRIPTION
                "When envTemperature2C reaches or goes below this value
                a trap will be generated signifying a low temperature
                condition at temperature sensor 2.  The LowLimitC
                variable is stored in non-volatile memory."
        ::= { envTemperature2 10 }

--
-- Temperature Input 3
--

        envTemperature3 OBJECT IDENTIFIER
        ::= { envTemperatureSensors 3 }

        envTemperature3State OBJECT-TYPE
            SYNTAX INTEGER { notInstalled(1),
                             airSensorInstalled(2),
                             waterSensorInstalled(3) }
            MAX-ACCESS read-write
            STATUS current
            DESCRIPTION
                "The state of use of Temperature Input Number 3.

                When a water temperature sensor is connected to
                Temperature Input 3 set State to waterSensorInstalled(3),
                when and air temperature sensor is connected set State
                to airSensorInstalled(2).  When no sensor is connected
                to Temperature Input 3 set State to notInstalled(1) to
                indicate that the value of envTemperature3F and
                envTemperature3C may not be valid.

		This variable is stored in non-volatile memory."
        ::= { envTemperature3 1 }

        envTemperature3F  OBJECT-TYPE
            SYNTAX Integer32
            MAX-ACCESS read-only
            STATUS current
            DESCRIPTION
                "The temperature for sensor 3 in degrees
                Fahrenheit."
        ::= { envTemperature3 2 }

        envTemperature3C  OBJECT-TYPE
            SYNTAX Integer32
            MAX-ACCESS read-only
            STATUS current
            DESCRIPTION
                "The temperature for sensor 3 in degrees
                Centigrade."
        ::= { envTemperature3 3 }

        envTemperature3Label OBJECT-TYPE
            SYNTAX DisplayString (SIZE (64))
            MAX-ACCESS read-write
            STATUS current
            DESCRIPTION
                "A user-defined text string associated with
                Temperature Input Number 3.  The text string is
                stored in non-volatile memory."
        ::= { envTemperature3 4 }

        envTemperature3OffsetF OBJECT-TYPE
            SYNTAX Integer32
            MAX-ACCESS read-write
            STATUS current
            DESCRIPTION
                "A temperature correction Offset associated with
                the envTemperature3F variable.

                The value of OffsetF is added to the value from
                Temperature Sensor Number 3 to obtain the value of
                the envTemperature3F variable.  When this variable is
                changed the envTemperature3OffsetF variable may also
                be effected.  The OffsetF variable is stored in
                in non-volatile memory."
        ::= { envTemperature3 5 }

        envTemperature3OffsetC OBJECT-TYPE
            SYNTAX Integer32
            MAX-ACCESS read-write
            STATUS current
            DESCRIPTION
                "A temperature correction Offset associated with
                the envTemperature3C variable.

                The value of OffsetC is added to the value from
                Temperature Sensor Number 3 to obtain the value of
                the envTemperature3C variable.  When this variable is
                changed the envTemperature3OffsetF variable may also
                be effected.  The OffsetC variable is stored in
                in non-volatile memory."
        ::= { envTemperature3 6 }

        envTemp3HighLimitF OBJECT-TYPE
            SYNTAX Integer32
            MAX-ACCESS read-write
            STATUS current
            DESCRIPTION
                "When envTemperature3F reaches or exceeds this value
                a trap will be generated signifying a high temperature
                condition at temperature sensor 3.  The HighLimitF
                variable is stored in non-volatile memory."
        ::= { envTemperature3 7 }

        envTemp3HighLimitC OBJECT-TYPE
            SYNTAX Integer32
            MAX-ACCESS read-write
            STATUS current
            DESCRIPTION
                "When envTemperature3C reaches or exceeds this value
                a trap will be generated signifying a high temperature
                condition at temperature sensor 3.  The HighLimitC
                variable is stored in non-volatile memory."
        ::= { envTemperature3 8 }

        envTemp3LowLimitF OBJECT-TYPE
            SYNTAX Integer32
            MAX-ACCESS read-write
            STATUS current
            DESCRIPTION
                "When envTemperature3F reaches or goes below this value
                a trap will be generated signifying a low temperature
                condition at temperature sensor 3.  The LowLimitF
                variable is stored in non-volatile memory."
        ::= { envTemperature3 9 }

        envTemp3LowLimitC OBJECT-TYPE
            SYNTAX Integer32
            MAX-ACCESS read-write
            STATUS current
            DESCRIPTION
                "When envTemperature3C reaches or goes below this value
                a trap will be generated signifying a low temperature
                condition at temperature sensor 3.  The LowLimitC
                variable is stored in non-volatile memory."
        ::= { envTemperature3 10 }

        envTemp3Calibrate OBJECT-TYPE
            SYNTAX INTEGER { on(1), off(2) }
            MAX-ACCESS read-write
            STATUS current
            DESCRIPTION
                "A temperature Offset correction routine associated
                with Temperature Sensor Number 3.

                When Calibrate is set to on(1) and State is set to
                waterSensorInstalled(3) the agent runs a self
                calibration routine which automatically adjusts the
                OffsetF and OffsetC variables."
        ::= { envTemperature3 11 }


--
-- Humidity Sensor Inputs
--
        envHumiditySensors OBJECT IDENTIFIER ::= { envMIB 8 }

--
-- Humidity Input 1
--

        envHumidity1 OBJECT IDENTIFIER
        ::= { envHumiditySensors 1 }

        envHumidity1State OBJECT-TYPE
            SYNTAX INTEGER { notInstalled(1), installed(2) }
            MAX-ACCESS read-write
            STATUS current
            DESCRIPTION
                "The state of use of Humidity Input Number 1.

                When a sensor is connected to Humidity Input 1
                set State to installed(2) to indicate that the
                value of envHumidity1RH is valid.  When no sensor
                is connected to Humidity Input 1 set State to
                notInstalled(1) to indicate that the value of
                envHumidity1RH may not be valid.

		This variable is stored in non-volatile memory."

        ::= { envHumidity1 1 }

        envHumidity1RH  OBJECT-TYPE
            SYNTAX Integer32
            MAX-ACCESS read-only
            STATUS current
            DESCRIPTION
                "The humidity for sensor 1 in percent RH."
        ::= { envHumidity1 2 }

        envHumidity1Label OBJECT-TYPE
            SYNTAX DisplayString (SIZE (64))
            MAX-ACCESS read-write
            STATUS current
            DESCRIPTION
                "A user-defined text string associated with
                Humidity Input Number 1.  The text string is
                stored in non-volatile memory."
        ::= { envHumidity1 3 }

        envHumidity1Offset OBJECT-TYPE
            SYNTAX Integer32
            MAX-ACCESS read-write
            STATUS current
            DESCRIPTION
                "A humidity correction Offset associated with
                the envHumidity1RH variable.

                The value of Offset is added to the value from
                Humidity Sensor Number 1 to obtain the value of
                the envHumidity1RH variable.  The Offset variable
                is stored in non-volatile memory."
        ::= { envHumidity1 4 }

        envHumidity1HighLimit OBJECT-TYPE
            SYNTAX Integer32
            MAX-ACCESS read-write
            STATUS current
            DESCRIPTION
                "When envHumidity1RH reaches or exceeds this value
                a trap will be generated signifying a high humidity
                condition at humidity sensor 1.  The HighLimit
                variable is stored in non-volatile memory."
        ::= { envHumidity1 5 }

        envHumidity1LowLimit OBJECT-TYPE
            SYNTAX Integer32
            MAX-ACCESS read-write
            STATUS current
            DESCRIPTION
                "When envHumidity1RH reaches or goes below this value
                a trap will be generated signifying a low humidity
                condition at humidity sensor 1.  The LowLimit
                variable is stored in non-volatile memory."
        ::= { envHumidity1 6 }

--
-- Huimidity Input 2
--

        envHumidity2 OBJECT IDENTIFIER
        ::= { envHumiditySensors 2 }

        envHumidity2State OBJECT-TYPE
            SYNTAX INTEGER { notInstalled(1), installed(2) }
            MAX-ACCESS read-write
            STATUS current
            DESCRIPTION
                "The state of use of Humidity Input Number 2.

                When a sensor is connected to Humidity Input 2
                set State to installed(2) to indicate that the
                value of envHumidity2RH is valid.  When no sensor
                is connected to Humidity Input 2 set State to
                notInstalled(1) to indicate that the value of
                envHumidity2RH may not be valid.

		This variable is stored in non-volatile memory."
        ::= { envHumidity2 1 }

        envHumidity2RH  OBJECT-TYPE
            SYNTAX Integer32
            MAX-ACCESS read-only
            STATUS current
            DESCRIPTION
                "The humidity for sensor 2 in percent RH."
        ::= { envHumidity2 2 }

        envHumidity2Label OBJECT-TYPE
            SYNTAX DisplayString (SIZE (64))
            MAX-ACCESS read-write
            STATUS current
            DESCRIPTION
                "A user-defined text string associated with
                Humidity Input Number 2.  The text string is
                stored in non-volatile memory."
        ::= { envHumidity2 3 }

        envHumidity2Offset OBJECT-TYPE
            SYNTAX Integer32
            MAX-ACCESS read-write
            STATUS current
            DESCRIPTION
                "A humidity correction Offset associated with
                the envHumidity2RH variable.

                The value of Offset is added to the value from
                Humidity Sensor Number 2 to obtain the value of
                the envHumidity2RH variable.  The Offset variable
                is stored in non-volatile memory."
        ::= { envHumidity2 4 }

        envHumidity2HighLimit OBJECT-TYPE
            SYNTAX Integer32
            MAX-ACCESS read-write
            STATUS current
            DESCRIPTION
                "When envHumidity2RH reaches or exceeds this value
                a trap will be generated signifying a high humidity
                condition at humidity sensor 2.  The HighLimit
                variable is stored in non-volatile memory."
        ::= { envHumidity2 5 }

        envHumidity2LowLimit OBJECT-TYPE
            SYNTAX Integer32
            MAX-ACCESS read-write
            STATUS current
            DESCRIPTION
                "When envHumidity2RH reaches or goes below this value
                a trap will be generated signifying a low humidity
                condition at humidity sensor 2.  The LowLimit
                variable is stored in non-volatile memory."
        ::= { envHumidity2 6 }

--
--  Environmental traps
--
        envTraps OBJECT IDENTIFIER ::= { envMIB 11 }

        envSummaryAlarmTrap NOTIFICATION-TYPE
	    STATUS current
            DESCRIPTION
                "An envSummaryAlarmTrap is generated each time a digital
                input State variable changes to true(1) or whenever a
                temperature or humidity goes above the HighLimit or below
                the LowLimit."
        ::= { envTraps 1 }

        envDigInput1TrueTrap NOTIFICATION-TYPE
	    STATUS current
            DESCRIPTION
                "An envDigInput1TrueTrap signifies that
                envDigitalInput1State has changed from false(2) to
                true(1).

                This trap is not generated if
                envDigInput1TrapEnabled is not true(1)."
        ::=  { envTraps 2 }

        envDigInput1FalseTrap NOTIFICATION-TYPE
	    STATUS current
            DESCRIPTION
                "An envDigInput1FalseTrap signifies that
                envDigitalInput1State has changed from true(1) to
                false(2).

                This trap is not generated if
                envDigInput1TrapEnabled is not true(1)."
        ::=  { envTraps 3 }

        envDigInput2TrueTrap NOTIFICATION-TYPE
	    STATUS current
            DESCRIPTION
                "An envDigInput2TrueTrap signifies that
                envDigitalInput2State has changed from false(2) to
                true(1).

                This trap is not generated if
                envDigInput2TrapEnabled is not true(1)."
        ::= { envTraps  4 }

        envDigInput2FalseTrap NOTIFICATION-TYPE
	    STATUS current
            DESCRIPTION
                "An envDigInput2FalseTrap signifies that
                envDigitalInput2State has changed from true(1) to
                false(2).

                This trap is not generated if
                envDigInput2TrapEnabled is not true(1)."
        ::=  { envTraps 5 }

        envDigInput3TrueTrap NOTIFICATION-TYPE
	    STATUS current
            DESCRIPTION
                "An envDigInput3TrueTrap signifies that
                envDigitalInput3State has changed from false(2) to
                true(1).

                This trap is not generated if
                envDigInput3TrapEnabled is not true(1)."
        ::=  { envTraps 6 }

        envDigInput3FalseTrap NOTIFICATION-TYPE
	    STATUS current
            DESCRIPTION
                "An envDigInput3FalseTrap signifies that
                envDigitalInput3State has changed from true(1) to
                false(2).

                This trap is not generated if
                envDigInput3TrapEnabled is not true(1)."
        ::=  { envTraps 7 }

        envDigInput4TrueTrap NOTIFICATION-TYPE
	    STATUS current
            DESCRIPTION
                "An envDigInput4TrueTrap signifies that
                envDigitalInput4State has changed from false(2) to
                true(1).

                This trap is not generated if
                envDigInput4TrapEnabled is not true(1)."
        ::=  { envTraps 8 }

        envDigInput4FalseTrap NOTIFICATION-TYPE
	    STATUS current
            DESCRIPTION
                "An envDigInput4FalseTrap signifies that
                envDigitalInput4State has changed from true(1) to
                false(2).

                This trap is not generated if
                envDigInput4TrapEnabled is not true(1)."
        ::=  { envTraps 9 }

        envDigInput5TrueTrap NOTIFICATION-TYPE
	    STATUS current
            DESCRIPTION
                "An envDigInput5TrueTrap signifies that
                envDigitalInput5State has changed from false(2) to
                true(1).

                This trap is not generated if
                envDigInput5TrapEnabled is not true(1)."
        ::=  { envTraps 10 }

        envDigInput5FalseTrap NOTIFICATION-TYPE
	    STATUS current
            DESCRIPTION
                "An envDigInput5FalseTrap signifies that
                envDigitalInput5State has changed from true(1) to
                false(2).

                This trap is not generated if
                envDigInput5TrapEnabled is not true(1)."
        ::= { envTraps 11 }

        envDigInput6TrueTrap NOTIFICATION-TYPE
	    STATUS current
            DESCRIPTION
                "An envDigInput6TrueTrap signifies that
                envDigitalInput6State has changed from false(2) to
                true(1).

                This trap is not generated if
                envDigInput6TrapEnabled is not true(1)."
        ::= { envTraps 12 }

        envDigInput6FalseTrap NOTIFICATION-TYPE
	    STATUS current
            DESCRIPTION
                "An envDigInput6FalseTrap signifies that
                envDigitalInput6State has changed from true(1) to
                false(2).

                This trap is not generated if
                envDigInput6TrapEnabled is not true(1)."
        ::= { envTraps 13 }

        envDigInput7TrueTrap NOTIFICATION-TYPE
	    STATUS current
            DESCRIPTION
                "An envDigInput7TrueTrap signifies that
                envDigitalInput7State has changed from false(2) to
                true(1).

                This trap is not generated if
                envDigInput7TrapEnabled is not true(1)."
        ::= { envTraps 14 }

        envDigInput7FalseTrap NOTIFICATION-TYPE
	    STATUS current
            DESCRIPTION
                "An envDigInput7FalseTrap signifies that
                envDigitalInput7State has changed from true(1) to
                false(2).

                This trap is not generated if
                envDigInput7TrapEnabled is not true(1)."
        ::= { envTraps 15 }

        envDigInput8TrueTrap NOTIFICATION-TYPE
	    STATUS current
            DESCRIPTION
                "An envDigInput8TrueTrap signifies that
                envDigitalInput8State has changed from false(2) to
                true(1).

                This trap is not generated if
                envDigInput8TrapEnabled is not true(1)."
        ::= { envTraps 16 }

        envDigInput8FalseTrap NOTIFICATION-TYPE
	    STATUS current
            DESCRIPTION
                "An envDigInput8FalseTrap signifies that
                envDigitalInput8State has changed from true(1) to
                false(2).

                This trap is not generated if
                envDigInput8TrapEnabled is not true(1)."
        ::= { envTraps 17 }

        envDigInput9TrueTrap NOTIFICATION-TYPE
	    STATUS current
            DESCRIPTION
                "An envDigInput9TrueTrap signifies that
                envDigitalInput9State has changed from false(2) to
                true(1).

                This trap is not generated if
                envDigInput9TrapEnabled is not true(1)."
        ::= { envTraps 18 }

        envDigInput9FalseTrap NOTIFICATION-TYPE
	    STATUS current
            DESCRIPTION
                "An envDigInput9FalseTrap signifies that
                envDigitalInput9State has changed from true(1) to
                false(2).

                This trap is not generated if
                envDigInput9TrapEnabled is not true(1)."
        ::= { envTraps 19 }

        envDigInput10TrueTrap NOTIFICATION-TYPE
	    STATUS current
            DESCRIPTION
                "An envDigInput10TrueTrap signifies that
                envDigitalInput10State has changed from false(2) to
                true(1).

                This trap is not generated if
                envDigInput10TrapEnabled is not true(1)."
        ::= { envTraps 20 }

        envDigInput10FalseTrap NOTIFICATION-TYPE
	    STATUS current
            DESCRIPTION
                "An envDigInput10FalseTrap signifies that
                envDigitalInput10State has changed from true(1) to
                false(2).

                This trap is not generated if
                envDigInput10TrapEnabled is not true(1)."
        ::= { envTraps 21 }

        envTemperature1HighTrap NOTIFICATION-TYPE
	    STATUS current
            DESCRIPTION
                "An envTemperature1HighTrap signifies that the sensor
                reading has gone above the HighLimit value."
        ::= { envTraps 22 }

        envTemperature1LowTrap NOTIFICATION-TYPE
	    STATUS current
            DESCRIPTION
                "An envTemperature1LowTrap signifies that the sensor
                reading has gone below the LowLimit value."
        ::= { envTraps 23 }

        envTemperature1NormalTrap NOTIFICATION-TYPE
	    STATUS current
            DESCRIPTION
                "An envTemperature1NormalTrap signifies that the
                sensor reading has return to the range bounded by
                HighLimit and LowLimit."
        ::= { envTraps 24 }

        envTemperature2HighTrap NOTIFICATION-TYPE
	    STATUS current
            DESCRIPTION
                "An envTemperature2HighTrap signifies that the sensor
                reading has gone above the HighLimit value."
        ::= { envTraps 25 }

        envTemperature2LowTrap NOTIFICATION-TYPE
	    STATUS current
            DESCRIPTION
                "An envTemperature2LowTrap signifies that the sensor
                reading has gone below the LowLimit value."
        ::= { envTraps 26 }

        envTemperature2NormalTrap NOTIFICATION-TYPE
	    STATUS current
            DESCRIPTION
                "An envTemperature2NormalTrap signifies that the
                sensor reading has return to the range bounded by
                HighLimit and LowLimit."
        ::= { envTraps 27 }

        envTemperature3HighTrap NOTIFICATION-TYPE
	    STATUS current
            DESCRIPTION
                "An envTemperature3HighTrap signifies that the sensor
                reading has gone above the HighLimit value."
        ::= { envTraps 28 }

        envTemperature3LowTrap NOTIFICATION-TYPE
	    STATUS current
            DESCRIPTION
                "An envTemperature3LowTrap signifies that the sensor
                reading has gone below the LowLimit value."
        ::= { envTraps 29 }

        envTemperature3NormalTrap NOTIFICATION-TYPE
	    STATUS current
            DESCRIPTION
                "An envTemperature3NormalTrap signifies that the
                sensor reading has return to the range bounded by
                HighLimit and LowLimit."
        ::= { envTraps 30 }

        envHumidity1HighTrap NOTIFICATION-TYPE
	    STATUS current
            DESCRIPTION
                "An envHumidity1HighTrap signifies that the sensor
                reading has gone above the HighLimit value."
        ::= { envTraps 31 }

        envHumidity1LowTrap NOTIFICATION-TYPE
	    STATUS current
            DESCRIPTION
                "An envHumidity1LowTrap signifies that the sensor
                reading has gone below the LowLimit value."
        ::= { envTraps 32 }

        envHumidity1NormalTrap NOTIFICATION-TYPE
	    STATUS current
            DESCRIPTION
                "An envHumidity1NormalTrap signifies that the
                sensor reading has return to the range bounded by
                HighLimit and LowLimit."
        ::= { envTraps 33 }

        envHumidity2HighTrap NOTIFICATION-TYPE
	    STATUS current
            DESCRIPTION
                "An envHumidity2HighTrap signifies that the sensor
                reading has gone above the HighLimit value."
        ::= { envTraps 34 }

        envHumidity2LowTrap NOTIFICATION-TYPE
	    STATUS current
            DESCRIPTION
                "An envHumidity2LowTrap signifies that the sensor
                reading has gone below the LowLimit value."
        ::= { envTraps 35 }

        envHumidity2NormalTrap NOTIFICATION-TYPE
	    STATUS current
            DESCRIPTION
                "An envHumidity2NormalTrap signifies that the
                sensor reading has return to the range bounded by
                HighLimit and LowLimit."
        ::= { envTraps 36 }

--
-- Conformance Information
--
	envConformance	OBJECT IDENTIFIER ::= { envMIB 12 }

	envCompliances	OBJECT IDENTIFIER ::= { envConformance 1 }

-- 
-- Compliance Statements
--

--
-- Little Glass House Compliance
--
	envLGHCompliance MODULE-COMPLIANCE
	    STATUS current
	    DESCRIPTION
		"The compliance statement for a Liebert 
		Little Glass House environmental control
		unit."
	MODULE -- this module
	    MANDATORY-GROUPS	{ envLGHStdPDIGroup, envLGHStdCDIGroup }
	::= { envCompliances 1 }

--
-- Data Pad Compliance
--
	envDataPadCompliance MODULE-COMPLIANCE
	    STATUS current
	    DESCRIPTION
		"The compliance statement for a Liebert
		Data Pad environmental control unit."
	MODULE -- this module
	    MANDATORY-GROUPS	{ envDPStdPDIGroup, envDPStdCDIGroup }
	::= { envCompliances 2 }
		

--
-- Units of conformance
--

	envGroups	OBJECT IDENTIFIER ::= { envConformance 2 }

	envIdentGroup	OBJECT-GROUP
	    OBJECTS { envIdentManufacturer, envIdentModel,
                    envIdentSoftwareVersion, envIdentSpecific }
	    STATUS current
	    DESCRIPTION
		"The Identification variables common to all 
		environmental control units."
	::= { envGroups 1 }

	envDigInputsGroup	OBJECT-GROUP
	    OBJECTS { envDigInput1State, envDigInput1Label,
                envDigInput1Polarity, envDigInput1TrapEnabled,
		envDigInput2State, envDigInput2Label,
       		envDigInput2Polarity, envDigInput2TrapEnabled,
		envDigInput3State, envDigInput3Label,
     		envDigInput3Polarity, envDigInput3TrapEnabled,
		envDigInput4State, envDigInput4Label,
		envDigInput4Polarity, envDigInput4TrapEnabled,
		envDigInput5State, envDigInput5Label,
		envDigInput5Polarity, envDigInput5TrapEnabled,
		envDigInput6State, envDigInput6Label,
		envDigInput6Polarity, envDigInput6TrapEnabled,
		envDigInput7State, envDigInput7Label,
		envDigInput7Polarity, envDigInput7TrapEnabled,
		envDigInput8State, envDigInput8Label,
		envDigInput8Polarity, envDigInput8TrapEnabled,
		envDigInput9State, envDigInput9Label,
		envDigInput9Polarity, envDigInput9TrapEnabled,
		envDigInput10State, envDigInput10Label,
		envDigInput10Polarity, envDigInput10TrapEnabled }
	    STATUS current
	    DESCRIPTION
		"The digital inputs common to all environmental 
		control units."
	::= { envGroups 2 }

	envRelayOutputsGroup	OBJECT-GROUP
	    OBJECTS { envRelay1State, envRelay1Label, envRelay1Control,
		envRelay2State, envRelay2Label, envRelay2Control }
	    STATUS current
	    DESCRIPTION
		"The relay outputs common to all environmental 
		control units."
	::= { envGroups 3 }

	envIndicatorOutputsGroup	OBJECT-GROUP
	    OBJECTS { envAudibleState, envAudibleControl,
		envLED1State, envLED1Label, envLED1Control,
		envLED2State, envLED2Label, envLED2Control,
		envLED3State, envLED3Label, envLED3Control }
	    STATUS current
	    DESCRIPTION
		"The alarm outputs common to all environmental
		control units."
	::= { envGroups 4 }

	envReceptacleOutputsGroup	OBJECT-GROUP
	    OBJECTS { envReceptacle1State, envReceptacle1Label,
		envReceptacle2State, envReceptacle2Label,
		envReceptacle3State, envReceptacle3Label,
		envReceptacle4State, envReceptacle4Label }
	    STATUS current
	    DESCRIPTION
		"The receptacle outputs common to all environmental
		control units."
	::= { envGroups 5 }

	envAlarmsGroup	OBJECT-GROUP
	    OBJECTS { envSummaryAlarm }
	    STATUS current
	    DESCRIPTION
		"The alarm group common to all environmental
		control units."
	::= { envGroups 6 }

	envTempGroup	OBJECT-GROUP
	    OBJECTS { envTemperature1State, envTemperature1F,
                envTemperature1C, envTemperature1Label,
		envTemperature1OffsetF, envTemperature1OffsetC,
                envTemp1HighLimitF, envTemp1HighLimitC, 
		envTemp1LowLimitF, envTemp1LowLimitC,
		envTemperature2State, envTemperature2F,
		envTemperature2C, envTemperature2Label,
		envTemperature2OffsetF, envTemperature2OffsetC,
		envTemp2HighLimitF, envTemp2HighLimitC, 
		envTemp2LowLimitF, envTemp2LowLimitC,
		envTemperature3State, envTemperature3F,
		envTemperature3C, envTemperature3Label,
		envTemperature3OffsetF, envTemperature3OffsetC,
		envTemp3HighLimitF, envTemp3HighLimitC,
		envTemp3LowLimitF, envTemp3LowLimitC, envTemp3Calibrate }
	    STATUS current
	    DESCRIPTION
		"The temperature group common to all environmental
		control units."
	::= { envGroups 7 }

	envHumidityGroup	OBJECT-GROUP
	    OBJECTS { envHumidity1State, envHumidity1RH, envHumidity1Label,
		envHumidity1Offset, envHumidity1HighLimit, 
		envHumidity1LowLimit, 
		envHumidity2State, envHumidity2RH, envHumidity2Label,
		envHumidity2Offset, envHumidity2HighLimit,
		envHumidity2LowLimit }
	    STATUS current
	    DESCRIPTION
		"The humidity group common to all environmental
		control units."
	::= { envGroups 8 }


END

XYPLEX INTERNET MIB        18 Oct 91
            
            
            
            
            
            
                             Definitions of Managed Objects
                               for Xyplex Internet Systems
            
                                     18 October 1991
            
                            Xyplex Document Number 420-0542-A
            
                                       Xyplex, Inc.
                                  330 Codman Hill Road
                                  Boxborough, MA 01719
                                     (508) 264-9900
            
                                   support@xyplex.com
            
            
            1.  Status of this Memo
            
            This document is submitted to the Internet MIB repository 
            and to Xyplex users as a Xyplex private extension to the 
            SNMP MIB.  Distribution of this memo is unlimited.  Please 
            express comments to Xyplex.
            
            2.  Abstract
            
            This memo defines a private portion of the Management 
            Information Base (MIB), within the Xyplex branch, for use 
            with SNMP over various transport services, such as UDP or 
















            
            
                                                               [Page   1]


            
                                  XYPLEX INTERNET MIB        18 Oct 91
            
            
            
            Ethernet.  In particular, it defines objects for Internet 
            protocol stack management of Xyplex systems.
            
            This memo does not specify a standard for the Internet 
            community.  It describes a standard for Xyplex products.









































            
            
                                                               [Page   2]


            
                                  XYPLEX INTERNET MIB        18 Oct 91
            
            
            
            3.  Historical Perspective
            
            As reported in RFC 1052, IAB Recommendations for the 
            Development of Internet Network Management Standards [1], a 
            two-prong strategy for network management of TCP/IP-based 
            internets was undertaken.  In the short-term, the Simple 
            Network Management Protocol (SNMP), defined in RFC 1067, was 
            to be used to manage nodes in the Internet community.  In 
            the long-term, the use of the OSI network management 
            framework was to be examined.  Two documents were produced 
            to define the management information: RFC 1065, which 
            defined the Structure of Management Information (SMI), and 
            RFC 1066, which defined the Management Information Base 
            (MIB).  Both of these documents were designed so as to be 
            compatible with both the SNMP and the OSI network management 
            framework.
            
            This strategy was quite successful in the short-term: 
            Internet-based network management technology was fielded, by 
            both the research and commercial communities, within a few 
            months.  As a result of this, portions of the Internet 
            community became network manageable in a timely fashion.
            
            As reported in RFC 1109, Report of the Second Ad Hoc Network 
            Management Review Group [2], the requirements of the SNMP 
            and the OSI network management frameworks were more 
            different than anticipated.  As such, the requirement for 
            compatibility between the SMI/MIB and both frameworks was 
            suspended.  This action permitted the operational network 
            management framework, based on the SNMP, to respond to new 
            operational needs in the Internet community by producing 
            MIB-II.
            
            In May of 1990, the core documents were elevated to 
            "Standard Protocols" with "Recommended" status.  As such, 
            the Internet- standard network management framework consists 
            of: Structure and Identification of Management Information 
            for TCP/IP-based internets, RFC 1155 [4], which describes 
            how managed objects contained in the MIB are defined; 
            Management Information Base for Network Management of 
            TCP/IP-based internets, which describes the managed objects 
            contained in the MIB, RFC 1156 [5]; and, the Simple Network 
            Management Protocol, RFC 1157 [6], which defines the 
            protocol used to manage these objects.
            
            Consistent with the IAB directive to produce simple, 

            
            
                                                               [Page   3]


            
                                  XYPLEX INTERNET MIB        18 Oct 91
            
            
            
            workable systems in the short-term, the list of managed 
            objects defined in the Internet-standard MIB was derived by 
            taking only those elements which are considered essential.  
            However, the SMI defined three extensibility mechanisms: 
            one, the addition of new standard objects through the 
            definitions of new versions of the MIB; two, the addition of 
            widely-available but non- standard objects through the 
            experimental subtree; and three, the addition of private 
            objects through the enterprises subtree.  Such additional 
            objects can not only be used for vendor-specific elements, 
            but also for experimentation as required to further the 
            knowledge of which other objects are essential.
            
            This memo defines extensions to the MIB using the third 
            method.  It contains definitions of managed objects in 
            various Xyplex products, using ASN.1 conventions specified 
            in [10].





























            
            
                                                               [Page   4]


            
                                  XYPLEX INTERNET MIB        18 Oct 91
            
            
            
            4.  Objects
            
            Managed objects are accessed via a virtual information 
            store, termed the Management Information Base or MIB.  
            Objects in the MIB are defined using the subset of Abstract 
            Syntax Notation One (ASN.1) [7] defined in the SMI.  In 
            particular, each object has a name, a syntax, and an 
            encoding.  The name is an object identifier, an 
            administratively assigned name, which specifies an object 
            type.  The object type together with an object instance 
            serves to uniquely identify a specific instantiation of the 
            object.  For human convenience, we often use a textual 
            string, termed the OBJECT DESCRIPTOR, to also refer to the 
            object type.
            
            The syntax of an object type defines the abstract data 
            structure corresponding to that object type.  The ASN.1 
            language is used for this purpose.  However, the SMI [4] 
            purposely restricts the ASN.1 constructs which may be used. 
            These restrictions are explicitly made for simplicity.
            
            The encoding of an object type is simply how that object 
            type is represented using the object type's syntax.  
            Implicitly tied to the notion of an object type's syntax and 
            encoding is how the object type is represented when being 
            transmitted on the network.
            
            The SMI specifies the use of the basic encoding rules of 
            ASN.1 [8], subject to the additional requirements imposed by 
            the SNMP.
            
            
            4.1.  Format of Definitions
            
            Section 6 contains the specification of all object types 
            contained in this MIB module.  The object types are defined 
            using the conventions defined in the SMI, as amended by the 
            extensions specified in [9].








            
            
                                                               [Page   5]


            
                                  XYPLEX INTERNET MIB        18 Oct 91
            
            
            
            5.  Overview
            
            The Internet MIB contains information for managing the 
            Internet protocol stack implementation in Xyplex systems 
            where that information is not part of any Internet 
            standard.
            
            The Internet MIB contains two main groups.  The Internet 
            deprecated group is the Internet group from the Xyplex 
            MiniMIB [11].  This specification deprecates that group in 
            favor of a new Internet group with a better overall 
            structure.
            
            Implementation of the Internet deprecated group is an 
            individual product issue, based on the need for 
            compatibility with the MiniMIB implementation.
            
            The Internet MIB is mandatory for all Xyplex systems that 
            implement any part of the Internet protocol stack.
            
            The MIB comprises several groups that correspond in spirit 
            to the standard Internet MIB.  As in the standard MIB, these 
            groups are not implemented if the system does not have the 
            corresponding Internet functions.  For example, a system 
            that does not implement Domain name resolution does not 
            implement the Xyplex Internet Domain resolver group.
            
            As a convenience to the reader, the groups are:
            
                xIp
                xTcp
                snmpAgent
                domainResolver
                slip
                telnet
                tn3270
                kerberos
            
                portSecurity
                xremote
                rotary
            
            The IP group contains:
            
                ipGatewayAddress1
                ipGatewayAddress2

            
            
                                                               [Page   6]


            
                                  XYPLEX INTERNET MIB        18 Oct 91
            
            
            
                ipAutoSubnetMask
                ipReassembly
            
            The TCP group contains a table of ports:
            
                tcpPortConnectByAddress
                tcpPortWindowSize
            
            The SNMP Agent group contains:
            
                snmpAgentGetCommunity
                snmpAgentSetCommunity
                snmpAgentTrapCommunity
                snmpAgentGetClientNumber
                snmpAgentSetClientNumber
                snmpAgentTrapClientNumber
            
            The SNMP Agent group also contains three tables, one each 
            for Get, Set, and Trap, all with the following similar 
            contents, where "xxx" is replaced by the function "get", 
            "set", or "trap":
            
                xxxClientIndex
                xxxClientEntryStatus
                xxxClientAddressType
                xxxClientAddress
            
            The Domain Resolver group contains:
            
                domainResolverSuffix
                domainResolverAddress1
                domainResolverAddress2
                domainResolverTtl
                domainResolverNameNumber
            
            The Domain Resolver group also contains a table of Domain 
            names, with each entry comprising:
            
                nameName
                nameAddress
                nameStatus
                nameSource
                nameTtl
            
            The SLIP group contains a table of ports:
            

            
            
                                                               [Page   7]


            
                                  XYPLEX INTERNET MIB        18 Oct 91
            
            
            
                slipIndex
                slipState
                slipLocalAddress
                slipRemoteAddress
                slipMask
                slipPortPacketsReceived
                slipPortPacketsSent
                slipPortPacketsDiscarded
                slipPortPacketLengthErrors
                slipPortPacketChecksumErrors
                slipNetworkPacketsReceived
                slipNetworkPacketsSent
                slipNetworkPacketsDiscarded
            
            The Telnet group contains a table of serial and parallel 
            ports:
            
                telnetPortIncomingTcpPort
                telnetPortOutgoingTcpPort
                telnetPortNewlineTranslation
                telnetPortTerminalType
                telnetPortEorReflection
                telnetPortBinaryMode
            
            The Telnet group also contains a table of just serial 
            ports:
            
                telnetSerialPortOptionDisplay
                telnetSerialPortCsiEscape
            
                telnetSerialPortEchoMode
                telnetSerialPortNewlineMode
                telnetSerialPortTransmitMode
                telnetSerialPortTransmitCharacterTimes
            
                telnetSerialPortAbortOutputCharacter
                telnetSerialPortAttentionCharacter
                telnetSerialPortEraseKeyCharacter
                telnetSerialPortEraseLineCharacter
                telnetSerialPortInterruptCharacter
                telnetSerialPortQueryCharacter
                telnetSerialPortSynchronizeCharacter
            
            The tn3270 group contains:
            
                tn3270DeviceNumber

            
            
                                                               [Page   8]


            
                                  XYPLEX INTERNET MIB        18 Oct 91
            
            
            
                tn3270LanguageNumber
                tn3270PortKeymapStatus
            
            The tn3270 group also contains a table of terminal devices:
            
                tn3270DeviceName
                tn3270DeviceStatus
                tn3270DeviceType
                tn3270Device3278Model
                tn3270DeviceKeyNumber
                tn3270DeviceScreenNumber
            
            The tn3270 group also contains a table of key maps:
            
                tn3270KeyDeviceName
                tn3270KeyName
                tn3270KeyStatus
                tn3270KeyCharacterSequence
                tn3270KeyDescription
            
            The tn3270 group also contains a table of screen action 
            maps:
            
                tn3270ScreenDeviceName
                tn3270ScreenActionName
                tn3270ScreenStatus
                tn3270ScreenCharacterSequence
            
            The tn3270 group also contains a table of languages:
            
                tn3270LanguageName
                tn3270LanguageStatus
            
            The tn3270 group also contains an EBCDIC to ASCII map for 
            each language:
            
                eToALanguageName
                eToAOffset
                eToAValue
            
            The tn3270 group also contains an ASCII to EBCDIC map for 
            each language:
            
                aToELanguageName
                aToEOffset
                aToEValue

            
            
                                                               [Page   9]


            
                                  XYPLEX INTERNET MIB        18 Oct 91
            
            
            
            
            The tn3270 group also contains a table of ports:
            
                tn3270PortIndex
                tn3270PortDeviceName
                tn3270PortLanguageName
                tn3270PortExtendedAttributes
                tn3270PortEorNegotiation
                tn3270PortErrorLock
            
            The Kerberos group contains:
            
                kerbStatus
                kerbRealm
                kerbQueryLimit
                kerbMasterName
                kerbServerName1
                kerbServerName2
                kerbInsecureLogins
                kerbSecureLogins
                kerbSecureLoginsFailed
                kerbPasswordChangeFailed
                kerbError
                kerbErrorTime
                kerbMasterAccess
                kerbMasterAccessFailed
                kerbServerAccess1
                kerbServerAccessFailed1
                kerbServerAccess2
                kerbServerAccessFailed2
            
            The Kerberos group also contains a table of ports:
            
                kerbPortIndex
                kerbPortStatus
            
            The Port Security group contains:
            
                psEntryNumber
                psEntryNumberLimit
                psEntryInvalidIndex
            
            The Port Security group also contains a table of port 
            entries:
            
                psPortIndex

            
            
                                                               [Page  10]


            
                                  XYPLEX INTERNET MIB        18 Oct 91
            
            
            
                psPortDefaultInboundAccess
                psPortDefaultOutboundAccess
            
            The Port Security group also contains a table of security 
            entries:
            
                psEntryIndex
                psEntryStatus
                psEntryAddress
                psEntryMask
                psEntryAccess
                psEntryDirection
                psEntryPortMap
            
            The XREMOTE group contains:
            
                xremoteServerName1
                xremoteServerName2
                xremoteServerAccess1
                xremoteServerAccessFailed1
                xremoteServerAccess2
                xremoteServerAccessFailed2
                xremoteSessions
            
            The XREMOTE group also contains a table of ports:
            
                xremotePortXremote
            
            The Rotary group contains:
            
                rotaryNumber
            
            The Rotary group also contains a table of rotaries:
            
                rotaryAddress
                rotaryStatus
                rotaryPortMap









            
            
                                                               [Page  11]


            
                                  XYPLEX INTERNET MIB        18 Oct 91
            
            
            
            6.  Definitions
            
                    XYPLEX-INTERNET-MIB DEFINITIONS ::= BEGIN
            
                    IMPORTS
                            enterprises, Counter, Gauge, IpAddress
                                    FROM RFC1155-SMI
                            DisplayString
                                    FROM RFC1158-MIB
                            OBJECT-TYPE
                                    FROM RFC1212-CONCISE-MIB
                            DateTime, AddressType
                                    FROM XYPLEX-SYSTEM-MIB;
            
            xyplex          OBJECT IDENTIFIER ::= { enterprises 33 }
            xInternetDep    OBJECT IDENTIFIER ::= { xyplex 4 }
            xInternet       OBJECT IDENTIFIER ::= { xyplex 10 }
            
            -- Xyplex Internet subgroups
            
            xIp             OBJECT IDENTIFIER ::= { xInternet 1 }
            xTcp            OBJECT IDENTIFIER ::= { xInternet 2 }
            snmpAgent       OBJECT IDENTIFIER ::= { xInternet 3 }
            domainResolver  OBJECT IDENTIFIER ::= { xInternet 4 }
            slip            OBJECT IDENTIFIER ::= { xInternet 5 }
            telnet          OBJECT IDENTIFIER ::= { xInternet 6 }
            tn3270          OBJECT IDENTIFIER ::= { xInternet 7 }
            kerberos        OBJECT IDENTIFIER ::= { xInternet 8 }
            portSecurity    OBJECT IDENTIFIER ::= { xInternet 9 }
            xremote         OBJECT IDENTIFIER ::= { xInternet 10 }
            rotary          OBJECT IDENTIFIER ::= { xInternet 11 }
            
            -- This MIB module uses the extended OBJECT-TYPE macro as
            -- defined in [9]
            
            -- This is a MIB module for all Xyplex systems that
            -- implement IP









            
            
                                                               [Page  12]


            
                                  XYPLEX INTERNET MIB        18 Oct 91
            
            
            
            -- the IP group
            
            -- Implementation of this group is mandatory for all Xyplex
            -- systems that implement IP
            
            ipGatewayAddress1 OBJECT-TYPE
                SYNTAX IpAddress
                ACCESS read-write
                STATUS mandatory
                DESCRIPTION
                    "The internet address of the system's primary (first 
                    choice) gateway.  A value of 0.0.0.0 indicates no 
                    address.  Corresponds directly to SERVER INTERNET 
                    PRIMARY GATEWAY ADDRESS and the value labeled 
                    'Primary Gateway Address:' in the SERVER INTERNET 
                    CHARACTERISTICS display."
                ::= { xIp 1 }
            
            ipGatewayAddress2 OBJECT-TYPE
                SYNTAX IpAddress
                ACCESS read-write
                STATUS mandatory
                DESCRIPTION
                    "The internet address of the system's secondary 
                    (second choice) gateway.  A value of 0.0.0.0 
                    indicates no address.  Corresponds directly to 
                    SERVER INTERNET SECONDARY GATEWAY ADDRESS and the 
                    value labeled 'Secondary Gateway Address:' in the 
                    SERVER INTERNET CHARACTERISTICS display."
                ::= { xIp 2 }
            
            ipAutoSubnetMask OBJECT-TYPE
                SYNTAX INTEGER { disabled(1), enabled(2) }
                ACCESS read-write
                STATUS mandatory
                DESCRIPTION
                    "A control for automatic determination of subnet 
                    mask.  'disabled' indicates the system must use the 
                    mask as configured by the network manager.  
                    'enabled' indicates that the system is to 
                    automatically change the subnet mask when the 
                    system's Internet address is changed.  Corresponds 
                    directly to SERVER INTERNET SUBNET MASK 
                    AUTOCONFIGURE and the value labeled 'Subnet Mask 
                    Autoconfigure:' in the SERVER INTERNET 
                    CHARACTERISTICS display."

            
            
                                                               [Page  13]


            
                                  XYPLEX INTERNET MIB        18 Oct 91
            
            
            
                ::= { xIp 3 }
            
            ipReassembly OBJECT-TYPE
                SYNTAX INTEGER { disabled(1), enabled(2) }
                ACCESS read-write
                STATUS mandatory
                DESCRIPTION
                    "A control for reassembly of IP fragments.  
                    Corresponds directly to SERVER INTERNET REASSEMBLY 
                    and the value labeled 'Reassembly:' in the SERVER 
                    INTERNET CHARACTERISTICS display."
                ::= { xIp 4 }


































            
            
                                                               [Page  14]


            
                                  XYPLEX INTERNET MIB        18 Oct 91
            
            
            
            -- the TCP group
            
            -- Implementation of this group is mandatory for all Xyplex
            -- systems that implement TCP
            
            -- the TCP Character Port table
            
            tcpPortTable OBJECT-TYPE
                SYNTAX SEQUENCE OF TcpPortEntry
                ACCESS not-accessible
                STATUS mandatory
                DESCRIPTION
                    "A list of TCP character port entries."
                ::= { xTcp 1 }
            
            tcpPortEntry OBJECT-TYPE
                SYNTAX TcpPortEntry
                ACCESS not-accessible
                STATUS mandatory
                DESCRIPTION
                    "TCP parameter values for a character port."
                INDEX { tcpPortIndex }
                ::= { tcpPortTable 1 }
            
            TcpPortEntry ::=
                SEQUENCE {
                    tcpPortIndex
                        INTEGER,
                    tcpPortConnectByAddress
                        INTEGER,
                    tcpPortWindowSize
                        INTEGER
                }
            
            tcpPortIndex OBJECT-TYPE
                SYNTAX INTEGER
                ACCESS read-only
                STATUS mandatory
                DESCRIPTION
                    "An index value that uniquely identifies a port.  
                    The port identified by a particular value of this 
                    index is the same port as identified by 
                    charPortIndex in the Character MIB [11]."
                ::= { tcpPortEntry 1 }
            
            tcpPortConnectByAddress OBJECT-TYPE

            
            
                                                               [Page  15]


            
                                  XYPLEX INTERNET MIB        18 Oct 91
            
            
            
                SYNTAX INTEGER { disabled(1), enabled(2) }
                ACCESS read-write
                STATUS mandatory
                DESCRIPTION
                    "A control for requesting outgoing connection by 
                    internet address.  'disabled' indicates outgoing 
                    connections must be by Domain name.  'enabled' 
                    indicates that outgoing connections may be requested 
                    by internet address.  Corresponds directly to PORT 
                    INTERNET CONNECTIONS and the presence of the label 
                    'Internet Connections' following the label 'Enabled 
                    Characteristics:' in the PORT CHARACTERISTICS 
                    display."
                ::= { tcpPortEntry 2 }
            
            tcpPortWindowSize OBJECT-TYPE
                SYNTAX INTEGER (64..8192)
                ACCESS read-write
                STATUS mandatory
                DESCRIPTION
                    "Size of the TCP window for TCP connections on the 
                    port.  Corresponds directly to PORT INTERNET TCP 
                    WINDOW SIZE and the value labeled 'TCP Window Size:' 
                    in the PORT ALTERNATE CHARACTERISTICS display."
                ::= { tcpPortEntry 3 }





















            
            
                                                               [Page  16]


            
                                  XYPLEX INTERNET MIB        18 Oct 91
            
            
            
            -- the SNMP Agent group
            
            -- Implementation of this group is mandatory for all Xyplex
            -- systems that implement SNMP
            
            snmpAgentGetCommunity OBJECT-TYPE
                SYNTAX DisplayString (SIZE (0..32))
                ACCESS read-write
                STATUS mandatory
                DESCRIPTION
                    "The SNMP community name allowed to perform 
                    get-requests or get-next requests to this agent.  
                    Use of this value is case-insensitive.  If the size 
                    is 0, the agent does not check the community name 
                    for these operations.  Corresponds directly to 
                    SERVER INTERNET SNMP GET COMMUNITY and the value 
                    labeled 'Get Community:' in the SERVER INTERNET SNMP 
                    CHARACTERISTICS display."
                ::= { snmpAgent 1 }
            
            snmpAgentSetCommunity OBJECT-TYPE
                SYNTAX DisplayString (SIZE (0..32))
                ACCESS read-write
                STATUS mandatory
                DESCRIPTION
                    "The SNMP community name allowed to perform 
                    set-requests to this agent.  Use of this value is 
                    case-insensitive.  If the size is 0, the agent does 
                    not check the community name for these operations.  
                    Corresponds directly to SERVER INTERNET SNMP SET 
                    COMMUNITY and the value labeled 'Set Community:' in 
                    the SERVER INTERNET SNMP CHARACTERISTICS display."
                ::= { snmpAgent 2 }
            
            snmpAgentTrapCommunity OBJECT-TYPE
                SYNTAX DisplayString (SIZE (0..32))
                ACCESS read-write
                STATUS mandatory
                DESCRIPTION
                    "The SNMP community name sent in traps from this 
                    agent.  Use of this value preserves case.  
                    Corresponds directly to SERVER INTERNET SNMP TRAP 
                    COMMUNITY and the value labeled 'Trap Community:' in 
                    the SERVER INTERNET SNMP CHARACTERISTICS display."
                ::= { snmpAgent 3 }
            

            
            
                                                               [Page  17]


            
                                  XYPLEX INTERNET MIB        18 Oct 91
            
            
            
            snmpAgentGetClientNumber OBJECT-TYPE
                SYNTAX INTEGER
                ACCESS read-only
                STATUS mandatory
                DESCRIPTION
                    "The number of client source addresses allowed to 
                    perform get-requests or get-next requests to this 
                    agent.  If the value is 0, the agent does not check 
                    source address for these operations.  Corresponds 
                    indirectly to the values labeled 'Get Client n:' in 
                    the SERVER INTERNET SNMP CHARACTERISTICS display."
                ::= { snmpAgent 4 }
            
            snmpAgentSetClientNumber OBJECT-TYPE
                SYNTAX INTEGER
                ACCESS read-only
                STATUS mandatory
                DESCRIPTION
                    "The number of client source addresses allowed to 
                    perform set-requests to this agent.  If the value is 
                    0, the agent does not check source address for these 
                    operations.  Corresponds indirectly to the values 
                    labeled 'Set Client n:' in the SERVER INTERNET SNMP 
                    CHARACTERISTICS display."
                ::= { snmpAgent 5 }
            
            snmpAgentTrapClientNumber OBJECT-TYPE
                SYNTAX INTEGER
                ACCESS read-only
                STATUS mandatory
                DESCRIPTION
                    "The number of client source addresses to which this 
                    agent sends traps.  If the value is 0, the agent 
                    does not perform this operation.  Corresponds 
                    indirectly to the values labeled 'Trap Client n:' in 
                    the SERVER INTERNET SNMP CHARACTERISTICS display."
                ::= { snmpAgent 6 }









            
            
                                                               [Page  18]


            
                                  XYPLEX INTERNET MIB        18 Oct 91
            
            
            
            -- the Get Client table
            
            getClientTable OBJECT-TYPE
                SYNTAX SEQUENCE OF GetClientEntry
                ACCESS not-accessible
                STATUS mandatory
                DESCRIPTION
                    "A list of get client entries.  The number of 
                    entries is given by the value of 
                    snmpAgentGetClientNumber."
                ::= { snmpAgent 7 }
            
            getClientEntry OBJECT-TYPE
                SYNTAX GetClientEntry
                ACCESS not-accessible
                STATUS mandatory
                DESCRIPTION
                    "Parameter values for a get client."
                INDEX { getClientIndex }
                ::= { getClientTable 1 }
            
            GetClientEntry ::=
                SEQUENCE {
                    getClientIndex
                        INTEGER,
                    getClientEntryStatus
                        INTEGER,
                    getClientAddressType
                        INTEGER,
                    getClientAddress
                        OCTET STRING
                }
            
            getClientIndex OBJECT-TYPE
                SYNTAX INTEGER
                ACCESS read-only
                STATUS mandatory
                DESCRIPTION
                    "Identification of a get client entry.  Corresponds 
                    directly to the number in the label 'Get Client n:' 
                    in the SERVER INTERNET SNMP CHARACTERISTICS 
                    display."
                ::= { getClientEntry 1 }
            
            getClientEntryStatus OBJECT-TYPE
                SYNTAX INTEGER { invalid(1), valid(2) }

            
            
                                                               [Page  19]


            
                                  XYPLEX INTERNET MIB        18 Oct 91
            
            
            
                ACCESS read-write
                STATUS mandatory
                DESCRIPTION
                    "Status of this entry.  Setting the value to 
                    'invalid' invalidates the entry.  It is an 
                    implementation-specific matter as to whether the 
                    agent removes an invalidated entry from the table."
                DEFVAL { valid }
                ::= { getClientEntry 2 }
            
            getClientAddressType OBJECT-TYPE
                SYNTAX AddressType
                ACCESS read-write
                STATUS mandatory
                DESCRIPTION
                    "The type of network address contained in 
                    getClientAddress.  'unknown' means no address has 
                    been defined.  'other' means no other type value 
                    applies.  'ip' is an Internet IP address.  
                    'ethernet' is an 802.3 MAC address.  If 
                    getClientAddressType does not accompany 
                    getClientAddress in a set request, the default type 
                    is 'ip'.  Corresponds indirectly to the address 
                    value labeled 'Get Client n:' in the SERVER INTERNET 
                    SNMP CHARACTERISTICS display."
                DEFVAL { unknown }
                ::= { getClientEntry 3 }
            
            getClientAddress OBJECT-TYPE
                SYNTAX OCTET STRING
                ACCESS read-write
                STATUS mandatory
                DESCRIPTION
                    "The client's network address.  If 
                    getClientAddressType does not accompany 
                    getClientAddress in a set request, the default type 
                    is 'ip'.  Corresponds directly to the address value 
                    labeled 'Get Client n:' in the SERVER INTERNET SNMP 
                    CHARACTERISTICS display."
                DEFVAL { null }  -- 'null' indicates zero length
                ::= { getClientEntry 4 }





            
            
                                                               [Page  20]


            
                                  XYPLEX INTERNET MIB        18 Oct 91
            
            
            
            -- the Set Client table
            
            setClientTable OBJECT-TYPE
                SYNTAX SEQUENCE OF SetClientEntry
                ACCESS not-accessible
                STATUS mandatory
                DESCRIPTION
                    "A list of set client entries.  The number of 
                    entries is given by the value of 
                    snmpAgentSetClientNumber."
                ::= { snmpAgent 8 }
            
            setClientEntry OBJECT-TYPE
                SYNTAX SetClientEntry
                ACCESS not-accessible
                STATUS mandatory
                DESCRIPTION
                    "Parameter values for a set client."
                INDEX { setClientIndex }
                ::= { setClientTable 1 }
            
            SetClientEntry ::=
                SEQUENCE {
                    setClientIndex
                        INTEGER,
                    setClientEntryStatus
                        INTEGER,
                    setClientAddressType
                        INTEGER,
                    setClientAddress
                        OCTET STRING
                }
            
            setClientIndex OBJECT-TYPE
                SYNTAX INTEGER
                ACCESS read-only
                STATUS mandatory
                DESCRIPTION
                    "Identification of a set client entry.  Corresponds 
                    directly to the number in the label 'Set Client n:' 
                    in the SERVER INTERNET SNMP CHARACTERISTICS 
                    display."
                ::= { setClientEntry 1 }
            
            setClientEntryStatus OBJECT-TYPE
                SYNTAX INTEGER { invalid(1), valid(2) }

            
            
                                                               [Page  21]


            
                                  XYPLEX INTERNET MIB        18 Oct 91
            
            
            
                ACCESS read-write
                STATUS mandatory
                DESCRIPTION
                    "Status of this entry.  Setting the value to 
                    'invalid' invalidates the entry.  It is an 
                    implementation-specific matter as to whether the 
                    agent removes an invalidated entry from the table."
                DEFVAL { valid }
                ::= { setClientEntry 2 }
            
            setClientAddressType OBJECT-TYPE
                SYNTAX AddressType
                ACCESS read-write
                STATUS mandatory
                DESCRIPTION
                    "The type of network address contained in 
                    setClientAddress.  'unknown' means no address has 
                    been defined.  'other' means no other type value 
                    applies.  'ip' is an Internet IP address.  
                    'ethernet' is an 802.3 MAC address.  If 
                    setClientAddressType does not accompany 
                    setClientAddress in a set request, the default type 
                    is 'ip'.  Corresponds indirectly to the address 
                    value labeled 'Set Client n:' in the SERVER INTERNET 
                    SNMP CHARACTERISTICS display."
                DEFVAL { unknown }
                ::= { setClientEntry 3 }
            
            setClientAddress OBJECT-TYPE
                SYNTAX OCTET STRING
                ACCESS read-write
                STATUS mandatory
                DESCRIPTION
                    "The client's network address.  When setting this 
                    value, the requester must supply 
                    setClientAddressType.  If setClientAddressType does 
                    not accompany setClientAddress in a set request, the 
                    default type is 'ip'.  Corresponds directly to the 
                    address value labeled 'Set Client n:' in the SERVER 
                    INTERNET SNMP CHARACTERISTICS display."
                DEFVAL { null }  -- 'null' indicates zero length
                ::= { setClientEntry 4 }




            
            
                                                               [Page  22]


            
                                  XYPLEX INTERNET MIB        18 Oct 91
            
            
            
            -- the Trap Client table
            
            trapClientTable OBJECT-TYPE
                SYNTAX SEQUENCE OF TrapClientEntry
                ACCESS not-accessible
                STATUS mandatory
                DESCRIPTION
                    "A list of trap client entries.  The number of 
                    entries is given by the value of 
                    snmpAgentTrapClientNumber."
                ::= { snmpAgent 9 }
            
            trapClientEntry OBJECT-TYPE
                SYNTAX TrapClientEntry
                ACCESS not-accessible
                STATUS mandatory
                DESCRIPTION
                    "Parameter values for a trap client."
                INDEX { trapClientIndex }
                ::= { trapClientTable 1 }
            
            TrapClientEntry ::=
                SEQUENCE {
                    trapClientIndex
                        INTEGER,
                    trapClientEntryStatus
                        INTEGER,
                    trapClientAddressType
                        INTEGER,
                    trapClientAddress
                        OCTET STRING
                }
            
            trapClientIndex OBJECT-TYPE
                SYNTAX INTEGER
                ACCESS read-only
                STATUS mandatory
                DESCRIPTION
                    "Identification of a trap client entry.  Corresponds 
                    directly to the number in the label 'Trap Client n:' 
                    in the SERVER INTERNET SNMP CHARACTERISTICS 
                    display."
                ::= { trapClientEntry 1 }
            
            trapClientEntryStatus OBJECT-TYPE
                SYNTAX INTEGER { invalid(1), valid(2) }

            
            
                                                               [Page  23]


            
                                  XYPLEX INTERNET MIB        18 Oct 91
            
            
            
                ACCESS read-write
                STATUS mandatory
                DESCRIPTION
                    "Status of this entry.  Setting the value to 
                    'invalid' invalidates the entry.  It is an 
                    implementation-specific matter as to whether the 
                    agent removes an invalidated entry from the table."
                DEFVAL { valid }
                ::= { trapClientEntry 2 }
            
            trapClientAddressType OBJECT-TYPE
                SYNTAX AddressType
                ACCESS read-write
                STATUS mandatory
                DESCRIPTION
                    "The type of network address contained in 
                    trapClientAddress.  'unknown' means no address has 
                    been defined.  'other' means no other type value 
                    applies.  'ip' is an Internet IP address.  
                    'ethernet' is an 802.3 MAC address.  If 
                    trapClientAddressType does not accompany 
                    trapClientAddress in a set request, the default type 
                    is 'ip'.  Corresponds indirectly to the address 
                    value labeled 'Trap Client n:' in the SERVER 
                    INTERNET SNMP CHARACTERISTICS display."
                DEFVAL { unknown }
                ::= { trapClientEntry 3 }
            
            trapClientAddress OBJECT-TYPE
                SYNTAX OCTET STRING
                ACCESS read-write
                STATUS mandatory
                DESCRIPTION
                    "The client's network address.  When setting this 
                    value, the requester must supply 
                    trapClientAddressType.  If trapClientAddressType 
                    does not accompany trapClientAddress in a set 
                    request, the default type is 'ip'.  Corresponds 
                    directly to the address value labeled 'Trap Client 
                    n:' in the SERVER INTERNET SNMP CHARACTERISTICS 
                    display."
                DEFVAL { null }  -- 'null' indicates zero length
                ::= { trapClientEntry 4 }



            
            
                                                               [Page  24]


            
                                  XYPLEX INTERNET MIB        18 Oct 91
            
            
            
            -- the Domain Resolver group
            
            -- Implementation of this group is mandatory for all Xyplex
            -- systems that implement Domain name resolution
            
            domainResolverSuffix OBJECT-TYPE
                SYNTAX DisplayString (SIZE (0..115))
                ACCESS read-write
                STATUS mandatory
                DESCRIPTION
                    "A partial domain name for the server to append to 
                    the end of an incomplete domain name provided by the 
                    user.  Corresponds directly to SERVER INTERNET 
                    DEFAULT DOMAIN SUFFIX and the value labeled 'Domain 
                    Suffix:' in the SERVER INTERNET CHARACTERISTICS 
                    display."
                ::= { domainResolver 1 }
            
            domainResolverAddress1 OBJECT-TYPE
                SYNTAX IpAddress
                ACCESS read-write
                STATUS mandatory
                DESCRIPTION
                    "The internet address of a Domain Name Server.  The 
                    system can use one or two such addresses, without 
                    preference.  A value of 0.0.0.0 indicates no 
                    address.  Corresponds directly to SERVER INTERNET 
                    PRIMARY DOMAIN ADDRESS and the value labeled 
                    'Primary Domain Address:' in the SERVER INTERNET 
                    CHARACTERISTICS display."
                ::= { domainResolver 2 }
            
            domainResolverAddress2 OBJECT-TYPE
                SYNTAX IpAddress
                ACCESS read-write
                STATUS mandatory
                DESCRIPTION
                    "The internet address of a Domain Name Server.  The 
                    system can use one or two such addresses, without 
                    preference.  A value of 0.0.0.0 indicates no 
                    address.  Corresponds directly to SERVER INTERNET 
                    SECONDARY DOMAIN ADDRESS and the value labeled 
                    'Secondary Domain Address:' in the SERVER INTERNET 
                    CHARACTERISTICS display."
                ::= { domainResolver 3 }
            

            
            
                                                               [Page  25]


            
                                  XYPLEX INTERNET MIB        18 Oct 91
            
            
            
            domainResolverTtl OBJECT-TYPE
                SYNTAX INTEGER (0..168)
                ACCESS read-write
                STATUS mandatory
                DESCRIPTION
                    "The number of hours to keep received Domain 
                    information.  Corresponds directly to SERVER 
                    INTERNET DOMAIN TTL and the value labeled ' Domain 
                    TTL:' in the SERVER INTERNET CHARACTERISTICS 
                    display."
                ::= { domainResolver 4 }
            
            domainResolverNameNumber OBJECT-TYPE
                SYNTAX INTEGER
                ACCESS read-only
                STATUS mandatory
                DESCRIPTION
                    "The number of Domain name mappings in this system's 
                    name cache."
                ::= { domainResolver 5 }


























            
            
                                                               [Page  26]


            
                                  XYPLEX INTERNET MIB        18 Oct 91
            
            
            
            -- the Name table
            
            nameTable OBJECT-TYPE
                SYNTAX SEQUENCE OF NameEntry
                ACCESS not-accessible
                STATUS mandatory
                DESCRIPTION
                    "A list of Domain name entries.  The number of 
                    entries is given by the value of 
                    domainResolverNameNumber."
                ::= { domainResolver 6 }
            
            nameEntry OBJECT-TYPE
                SYNTAX NameEntry
                ACCESS not-accessible
                STATUS mandatory
                DESCRIPTION
                    "Parameter values for a Domain name."
                INDEX { nameName, nameAddress }
                ::= { nameTable 1 }
            
            NameEntry ::=
                SEQUENCE {
                    nameName
                        DisplayString,
                    nameAddress
                        IpAddress,
                    nameStatus
                        INTEGER,
                    nameSource
                        INTEGER,
                    nameTtl
                        INTEGER
                }
            
            nameName OBJECT-TYPE
                SYNTAX DisplayString (SIZE (1..50))
                ACCESS read-only
                STATUS mandatory
                DESCRIPTION
                    "A fully qualified domain name.  Corresponds 
                    directly to the value labeled 'Domain Name' in the 
                    DOMAIN display."
                ::= { nameEntry 1 }
            
            nameAddress OBJECT-TYPE

            
            
                                                               [Page  27]


            
                                  XYPLEX INTERNET MIB        18 Oct 91
            
            
            
                SYNTAX IpAddress
                ACCESS read-write
                STATUS mandatory
                DESCRIPTION
                    "An Internet address corresponding to the Domain 
                    name.  Corresponds directly to the value labeled 
                    'Internet Address' in the DOMAIN display."
                ::= { nameEntry 2 }
            
            nameStatus OBJECT-TYPE
                SYNTAX INTEGER { invalid(1), valid(2) }
                ACCESS read-write
                STATUS mandatory
                DESCRIPTION
                    "The status of the entry.  Set to 'invalid' to 
                    remove the entry, which corresponds directly to the 
                    PURGE DOMAIN command.  Actual removal of the entry 
                    is implementation specific."
                ::= { nameEntry 3 }
            
            nameSource OBJECT-TYPE
                SYNTAX INTEGER { manager(1), primary(2), secondary(3) }
                ACCESS read-only
                STATUS mandatory
                DESCRIPTION
                    "Source of this entry.  The value meanings are:
            
                    local       defined by manager (LOCAL)
                    primary     obtained from a primary name server
                    secondary   obtained from a secondary name server
            
                    Corresponds directly to the value labeled 'Source' 
                    in the DOMAIN display."
                ::= { nameEntry 4 }
            
            nameTtl OBJECT-TYPE
                SYNTAX INTEGER
                ACCESS read-only
                STATUS mandatory
                DESCRIPTION
                    "The number of minutes remaining in the entry's time 
                    to live.  Corresponds directly to the value labeled 
                    'TTL' in the DOMAIN display."
                DEFVAL { domainResolverTtl }
                ::= { nameEntry 5 }

            
            
                                                               [Page  28]


            
                                  XYPLEX INTERNET MIB        18 Oct 91
            
            
            
            -- the SLIP group
            
            -- Implementation of this group is mandatory for all Xyplex
            -- systems that implement SLIP ports
            
            slipTable OBJECT-TYPE
                SYNTAX SEQUENCE OF SlipEntry
                ACCESS not-accessible
                STATUS mandatory
                DESCRIPTION
                    "A list of SLIP character port entries."
                ::= { slip 1 }
            
            slipEntry OBJECT-TYPE
                SYNTAX SlipEntry
                ACCESS not-accessible
                STATUS mandatory
                DESCRIPTION
                    "Parameter values for a SLIP port."
                INDEX { slipIndex }
                ::= { slipTable 1 }
            
            SlipEntry ::=
                SEQUENCE {
                    slipIndex
                        INTEGER,
                    slipState
                        INTEGER,
                    slipLocalAddress
                        IpAddress,
                    slipRemoteAddress
                        IpAddress,
                    slipMask
                        IpAddress,
                    slipPortPacketsReceived
                        Counter,
                    slipPortPacketsSent
                        Counter,
                    slipPortPacketsDiscarded
                        Counter,
                    slipPortPacketLengthErrors
                        Counter,
                    slipPortPacketChecksumErrors
                        Counter,
                    slipNetworkPacketsReceived
                        Counter,

            
            
                                                               [Page  29]


            
                                  XYPLEX INTERNET MIB        18 Oct 91
            
            
            
                    slipNetworkPacketsSent
                        Counter,
                    slipNetworkPacketsDiscarded
                        Counter
                }
            
            slipIndex OBJECT-TYPE
                SYNTAX INTEGER
                ACCESS read-only
                STATUS mandatory
                DESCRIPTION
                    "An index value that uniquely identifies a port that 
                    can run SLIP.  The port identified by a particular 
                    value of this index is the same port as identified 
                    by charPortIndex in the Character MIB [11]."
                ::= { slipEntry 1 }
            
            slipState OBJECT-TYPE
                SYNTAX INTEGER { off(1), on(2) }
                ACCESS read-write
                STATUS mandatory
                DESCRIPTION
                    "A control indicating whether SLIP is in operation 
                    on the port.  Corresponds directly to PORT INTERNET 
                    SLIP and the value labeled 'SLIP' in the PORT 
                    CHARACTERISTICS display."
                ::= { slipEntry 2 }
            
            slipLocalAddress OBJECT-TYPE
                SYNTAX IpAddress
                ACCESS read-write
                STATUS mandatory
                DESCRIPTION
                    "The IP address assigned to the port.  Corresponds 
                    directly to PORT SLIP ADDRESS and the value labeled 
                    'SLIP Address:' in the PORT ALTERNATE 
                    CHARACTERISTICS display."
                ::= { slipEntry 3 }
            
            slipRemoteAddress OBJECT-TYPE
                SYNTAX IpAddress
                ACCESS read-write
                STATUS mandatory
                DESCRIPTION
                    "The IP address of the remote system attached to the 
                    port.  Corresponds directly to PORT SLIP REMOTE and 

            
            
                                                               [Page  30]


            
                                  XYPLEX INTERNET MIB        18 Oct 91
            
            
            
                            the value labeled 'Remote SLIP Address:' in the PORT 
                    ALTERNATE CHARACTERISTICS display."
                ::= { slipEntry 4 }
            
            slipMask OBJECT-TYPE
                SYNTAX IpAddress
                ACCESS read-write
                STATUS mandatory
                DESCRIPTION
                    "The subnet mask to use for SLIP operation on the 
                    port.  Corresponds directly to PORT SLIP MASK and 
                    the value labeled 'SLIP Mask:' in the PORT ALTERNATE 
                    CHARACTERISTICS display."
                ::= { slipEntry 5 }
            
            slipPortPacketsReceived OBJECT-TYPE
                SYNTAX Counter
                ACCESS read-only
                STATUS mandatory
                DESCRIPTION
                    "The number of SLIP packets received from the port.  
                    Corresponds directly to the value labeled 'Serial 
                    Packets Received:' in the PORT COUNTERS display."
                ::= { slipEntry 6 }
            
            slipPortPacketsSent OBJECT-TYPE
                SYNTAX Counter
                ACCESS read-only
                STATUS mandatory
                DESCRIPTION
                    "The number of SLIP packets sent to the port.  
                    Corresponds directly to the value labeled 'Serial 
                    Packets Sent:' in the PORT COUNTERS display."
                ::= { slipEntry 7 }
            
            slipPortPacketsDiscarded OBJECT-TYPE
                SYNTAX Counter
                ACCESS read-only
                STATUS mandatory
                DESCRIPTION
                    "The number of SLIP packets received from the port 
                    and discarded.  Corresponds directly to the value 
                    labeled 'Serial Packets Discarded:' in the PORT 
                    COUNTERS display."
                ::= { slipEntry 8 }
            

            
            
                                                               [Page  31]


            
                                  XYPLEX INTERNET MIB        18 Oct 91
            
            
            
            slipPortPacketLengthErrors OBJECT-TYPE
                SYNTAX Counter
                ACCESS read-only
                STATUS mandatory
                DESCRIPTION
                    "The number of SLIP packets received from the port 
                    with an incorrect number of bytes.  Corresponds 
                    directly to the value labeled 'Serial Packet Length 
                    Errors:' in the PORT COUNTERS display."
                ::= { slipEntry 9 }
            
            slipPortPacketChecksumErrors OBJECT-TYPE
                SYNTAX Counter
                ACCESS read-only
                STATUS mandatory
                DESCRIPTION
                    "The number of SLIP packets received from the port 
                    with an invalid checksum.  Corresponds directly to 
                    the value labeled 'Serial Packet Checksum Errors:' 
                    in the PORT COUNTERS display."
                ::= { slipEntry 10 }
            
            slipNetworkPacketsReceived OBJECT-TYPE
                SYNTAX Counter
                ACCESS read-only
                STATUS mandatory
                DESCRIPTION
                    "The number of SLIP packets received from the 
                    network for this port.  Corresponds directly to the 
                    value labeled 'Network Packets Received:' in the 
                    PORT COUNTERS display."
                ::= { slipEntry 11 }
            
            slipNetworkPacketsSent OBJECT-TYPE
                SYNTAX Counter
                ACCESS read-only
                STATUS mandatory
                DESCRIPTION
                    "The number of SLIP packets sent to the network from 
                    this port.  Corresponds directly to the value 
                    labeled 'Network Packets Sent:' in the PORT COUNTERS 
                    display."
                ::= { slipEntry 12 }
            
            slipNetworkPacketsDiscarded OBJECT-TYPE
                SYNTAX Counter

            
            
                                                               [Page  32]


            
                                  XYPLEX INTERNET MIB        18 Oct 91
            
            
            
                ACCESS read-only
                STATUS mandatory
                DESCRIPTION
                    "The number of SLIP packets received from the 
                    network for this port and discarded.  Corresponds 
                    directly to the value labeled 'Network Packets 
                    Discarded:' in the PORT COUNTERS display."
                ::= { slipEntry 13 }






































            
            
                                                               [Page  33]


            
                                  XYPLEX INTERNET MIB        18 Oct 91
            
            
            
            -- the Telnet group
            
            -- Implementation of this group is mandatory for all Xyplex
            -- systems that implement Telnet
            
            -- the Telnet Character Port table
            
            -- Ports in this table are either serial or parallel
            
            telnetPortTable OBJECT-TYPE
                SYNTAX SEQUENCE OF TelnetPortEntry
                ACCESS not-accessible
                STATUS mandatory
                DESCRIPTION
                    "A list of Telnet character port entries."
                ::= { telnet 1 }
            
            telnetPortEntry OBJECT-TYPE
                SYNTAX TelnetPortEntry
                ACCESS not-accessible
                STATUS mandatory
                DESCRIPTION
                    "Telnet parameter values for a character port."
                INDEX { telnetPortIndex }
                ::= { telnetPortTable 1 }
            
            TelnetPortEntry ::=
                SEQUENCE {
                    telnetPortIndex
                        INTEGER,
                    telnetPortIncomingTcpPort
                        INTEGER,
                    telnetPortOutgoingTcpPort
                        INTEGER,
                    telnetPortNewlineTranslation
                        INTEGER,
                    telnetPortTerminalType
                        DisplayString,
                    telnetPortEorReflection
                        INTEGER,
                    telnetPortBinaryMode
                        INTEGER
                }
            
            telnetPortIndex OBJECT-TYPE
                SYNTAX INTEGER

            
            
                                                               [Page  34]


            
                                  XYPLEX INTERNET MIB        18 Oct 91
            
            
            
                ACCESS read-only
                STATUS mandatory
                DESCRIPTION
                    "An index value that uniquely identifies a port.  
                    The port identified by a particular value of this 
                    index is the same port as identified by 
                    charPortIndex in the Character MIB [11]."
                ::= { telnetPortEntry 1 }
            
            telnetPortIncomingTcpPort OBJECT-TYPE
                SYNTAX INTEGER (1..32767)
                ACCESS read-write
                STATUS mandatory
                DESCRIPTION
                    "The TCP port number offered for incoming 
                    connections to this character port.  Corresponds 
                    directly to PORT TELNET REMOTE PORT and the value 
                    labeled 'Remote Port:' in the PORT TELNET 
                    CHARACTERISTICS display."
                ::= { telnetPortEntry 2 }
            
            telnetPortOutgoingTcpPort OBJECT-TYPE
                SYNTAX INTEGER
                ACCESS read-only
                STATUS mandatory
                DESCRIPTION
                    "The TCP port number used by default for outgoing 
                    connections from this character port.  Corresponds 
                    directly to PORT TELNET DEFAULT PORT and the value 
                    labeled 'Default Port:' in the PORT TELNET 
                    CHARACTERISTICS display."
                ::= { telnetPortEntry 3 }
            
            telnetPortNewlineTranslation OBJECT-TYPE
                SYNTAX INTEGER { none(1), cr(2), crNull(3), crLf(4) }
                ACCESS read-write
                STATUS mandatory
                DESCRIPTION
                    "Translation to apply to newline sequences (CR/NULL 
                    or CR/LF) received from the network, before sending 
                    the newline to the character port.  The value 
                    indicates the sequence sent to the character port, 
                    with 'none' meaning no translation.  Corresponds 
                    directly to PORT TELNET NEWLINE FILTERING and the 
                    value labeled 'Newline Filtering:' in the PORT 
                    TELNET CHARACTERISTICS display."

            
            
                                                               [Page  35]


            
                                  XYPLEX INTERNET MIB        18 Oct 91
            
            
            
                ::= { telnetPortEntry 4 }
            
            telnetPortTerminalType OBJECT-TYPE
                SYNTAX DisplayString (SIZE (1..20))
                ACCESS read-write
                STATUS mandatory
                DESCRIPTION
                    "The terminal type character string for Telnet 
                    negotiations.  Corresponds directly to PORT TELNET 
                    TERMINALTYPE and the value labeled 'TerminalType:' 
                    in the PORT TELNET CHARACTERISTICS display."
                ::= { telnetPortEntry 5 }
            
            telnetPortEorReflection OBJECT-TYPE
                SYNTAX INTEGER { disabled(1), enabled(2) }
                ACCESS read-write
                STATUS mandatory
                DESCRIPTION
                    "Control for end-of-record handshake.  Corresponds 
                    directly to PORT TELNET EOR REFLECTION and the value 
                    labeled 'EOR Reflection:' in the PORT TELNET 
                    CHARACTERISTICS display."
                ::= { telnetPortEntry 6 }
            
            telnetPortBinaryMode OBJECT-TYPE
                SYNTAX INTEGER { flowControl(1), complete(2),
                                 disabled(3) }
                ACCESS read-write
                STATUS mandatory
                DESCRIPTION
                    "Control for operation of Telnet binary mode.  The 
                    value meanings are:
            
                    disabled      refuse binary mode negotiation
                                  (INTERACTIVE)
                    flowControl   pass all but XON and XOFF (PASTHRU)
                    complete      pass all characters (PASSALL)
            
                    Corresponds directly to PORT TELNET BINARY SESSION 
                    MODE and the value labeled 'Binary Session Mode:' in 
                    the PORT TELNET CHARACTERISTICS display."
                ::= { telnetPortEntry 7 }




            
            
                                                               [Page  36]


            
                                  XYPLEX INTERNET MIB        18 Oct 91
            
            
            
            -- the Telnet Serial Character Port table
            
            telnetSerialPortTable OBJECT-TYPE
                SYNTAX SEQUENCE OF TelnetSerialPortEntry
                ACCESS not-accessible
                STATUS mandatory
                DESCRIPTION
                    "A list of Telnet character port entries."
                ::= { telnet 2 }
            
            telnetSerialPortEntry OBJECT-TYPE
                SYNTAX TelnetSerialPortEntry
                ACCESS not-accessible
                STATUS mandatory
                DESCRIPTION
                    "Telnet parameter values for a character port."
                INDEX { telnetSerialPortIndex }
                ::= { telnetSerialPortTable 1 }
            
            TelnetSerialPortEntry ::=
                SEQUENCE {
                    telnetSerialPortIndex
                        INTEGER,
                    telnetSerialPortOptionDisplay
                        INTEGER,
                    telnetSerialPortCsiEscape
                        INTEGER,
                    telnetSerialPortEchoMode
                        INTEGER,
                    telnetSerialPortNewlineMode
                        INTEGER,
                    telnetSerialPortTransmitMode
                        INTEGER,
                    telnetSerialPortTransmitCharacterTimes
                        INTEGER,
                    telnetSerialPortAbortOutputCharacter
                        INTEGER,
                    telnetSerialPortAttentionCharacter
                        INTEGER,
                    telnetSerialPortEraseKeyCharacter
                        INTEGER,
                    telnetSerialPortEraseLineCharacter
                        INTEGER,
                    telnetSerialPortInterruptCharacter
                        INTEGER,
                    telnetSerialPortQueryCharacter

            
            
                                                               [Page  37]


            
                                  XYPLEX INTERNET MIB        18 Oct 91
            
            
            
                        INTEGER,
                    telnetSerialPortSynchronizeCharacter
                        INTEGER
                }
            
            telnetSerialPortIndex OBJECT-TYPE
                SYNTAX INTEGER
                ACCESS read-only
                STATUS mandatory
                DESCRIPTION
                    "An index value that uniquely identifies a port.  
                    The port identified by a particular value of this 
                    index is the same port as identified by 
                    charPortIndex in the Character MIB [11]."
                ::= { telnetSerialPortEntry 1 }
            
            telnetSerialPortOptionDisplay OBJECT-TYPE
                SYNTAX INTEGER { disabled(1), enabled(2) }
                ACCESS read-write
                STATUS mandatory
                DESCRIPTION
                    "Control for display of Telnet option negotiations.  
                    Corresponds directly to PORT TELNET OPTION DISPLAY 
                    and the value labeled 'Option Display:' in the PORT 
                    TELNET CHARACTERISTICS display."
                ::= { telnetSerialPortEntry 2 }
            
            telnetSerialPortCsiEscape OBJECT-TYPE
                SYNTAX INTEGER { disabled(1), enabled(2) }
                ACCESS read-write
                STATUS mandatory
                DESCRIPTION
                    "Control for translation of 8-bit escape sequences 
                    received from the character port to 7-bit 
                    equivalents before transmission to the remote 
                    partner.  Corresponds directly to PORT TELNET CSI 
                    ESCAPE and the value labeled 'CSI Escape:' in the 
                    PORT TELNET CHARACTERISTICS display."
                ::= { telnetSerialPortEntry 3 }
            
            telnetSerialPortEchoMode OBJECT-TYPE
                SYNTAX INTEGER { local(1), remote(2) }
                ACCESS read-write
                STATUS mandatory
                DESCRIPTION
                    "Control for who echoes characters that come from 

            
            
                                                               [Page  38]


            
                                  XYPLEX INTERNET MIB        18 Oct 91
            
            
            
                            the character port.  The value meanings are:
            
                    local    terminal server echoes locally
                    remote   remote system echoes
            
                    Corresponds directly to PORT TELNET ECHO MODE and 
                    the value labeled 'Echo Mode:' in the PORT TELNET 
                    CHARACTERISTICS display."
                ::= { telnetSerialPortEntry 4 }
            
            telnetSerialPortNewlineMode OBJECT-TYPE
                SYNTAX INTEGER { crNull(1), crLf(2), verbatim(3) }
                ACCESS read-write
                STATUS mandatory
                DESCRIPTION
                    "Translation to apply to newline (carriage return) 
                    received from the character port, before sending the 
                    newline to the remote partner.  The correspondence 
                    to command keywords is 'crNull' to NULL, 'crLF' to 
                    LINEFEED, and 'verbatim' to NOTHING (that is, no 
                    translation).  Corresponds directly to PORT TELNET 
                    NEWLINE and the value labeled 'Newline:' in the PORT 
                    TELNET CHARACTERISTICS display."
                ::= { telnetSerialPortEntry 5 }
            
            telnetSerialPortTransmitMode OBJECT-TYPE
                SYNTAX INTEGER { immediate(1), buffered(2), timed(3) }
                ACCESS read-write
                STATUS mandatory
                DESCRIPTION
                    "Criterion for deciding to send to the remote 
                    partner characters received from the character port.  
                    Corresponds directly to PORT TELNET TRANSMIT and the 
                    value labeled 'Transmit:' in the PORT TELNET 
                    CHARACTERISTICS display."
                ::= { telnetSerialPortEntry 6 }
            
            telnetSerialPortTransmitCharacterTimes OBJECT-TYPE
                SYNTAX INTEGER (1..255)
                ACCESS read-write
                STATUS mandatory
                DESCRIPTION
                    "Number of character times to wait before 
                    transmitting when telnetSerialPortTransmitMode value 
                    is 'timed'.  Corresponds directly to PORT TELNET 
                    TRANSMIT IDLETIME and the value labeled 'Transmit:  

            
            
                                                               [Page  39]


            
                                  XYPLEX INTERNET MIB        18 Oct 91
            
            
            
                            Idle Time -' in the PORT TELNET CHARACTERISTICS 
                    display."
                ::= { telnetSerialPortEntry 7 }
            
            telnetSerialPortAbortOutputCharacter OBJECT-TYPE
                SYNTAX INTEGER (0..255)
                ACCESS read-write
                STATUS mandatory
                DESCRIPTION
                    "Character input from the character port to cause 
                    aborting output.  The value 0 indicates no character 
                    has this effect.  Corresponds directly to PORT 
                    TELNET ABORT OUTPUT and the value labeled 'Abort 
                    Output Character:' in the PORT TELNET 
                    CHARACTERISTICS display."
                ::= { telnetSerialPortEntry 8 }
            
            telnetSerialPortAttentionCharacter OBJECT-TYPE
                SYNTAX INTEGER (0..255)
                ACCESS read-write
                STATUS mandatory
                DESCRIPTION
                    "Character input from the character port to cause an 
                    attention notification to the remote partner.  The 
                    value 0 indicates no character has this effect.  
                    Corresponds directly to PORT TELNET ATTENTION and 
                    the value labeled 'Attention Character:' in the PORT 
                    TELNET CHARACTERISTICS display."
                ::= { telnetSerialPortEntry 9 }
            
            telnetSerialPortEraseKeyCharacter OBJECT-TYPE
                SYNTAX INTEGER (0..255)
                ACCESS read-write
                STATUS mandatory
                DESCRIPTION
                    "Character input from the character port to cause 
                    erasure of the previous input character.  The value 
                    0 indicates no character has this effect.  
                    Corresponds directly to PORT TELNET ERASE CHARACTER 
                    and the value labeled 'Erase Keystroke Character:' 
                    in the PORT TELNET CHARACTERISTICS display."
                ::= { telnetSerialPortEntry 10 }
            
            telnetSerialPortEraseLineCharacter OBJECT-TYPE
                SYNTAX INTEGER (0..255)
                ACCESS read-write

            
            
                                                               [Page  40]


            
                                  XYPLEX INTERNET MIB        18 Oct 91
            
            
            
                STATUS mandatory
                DESCRIPTION
                    "Character input from the character port to cause 
                    erasure of the previous line of input.  The value 0 
                    indicates no character has this effect.  Corresponds 
                    directly to PORT TELNET ERASE LINE and the value 
                    labeled 'Erase Line Character:' in the PORT TELNET 
                    CHARACTERISTICS display."
                ::= { telnetSerialPortEntry 11 }
            
            telnetSerialPortInterruptCharacter OBJECT-TYPE
                SYNTAX INTEGER (0..255)
                ACCESS read-write
                STATUS mandatory
                DESCRIPTION
                    "Character input from the character port to cause 
                    sending an interrupt notification to the remote 
                    partner.  The value 0 indicates no character has 
                    this effect.  Corresponds directly to PORT TELNET 
                    INTERRUPT and the value labeled 'Interrupt 
                    Character:' in the PORT TELNET CHARACTERISTICS 
                    display."
                ::= { telnetSerialPortEntry 12 }
            
            telnetSerialPortQueryCharacter OBJECT-TYPE
                SYNTAX INTEGER (0..255)
                ACCESS read-write
                STATUS mandatory
                DESCRIPTION
                    "Character input from the character port to cause 
                    sending a status query to the remote partner.  The 
                    value 0 indicates no character has this effect.  
                    Corresponds directly to PORT TELNET QUERY and the 
                    value labeled 'Query Character:' in the PORT TELNET 
                    CHARACTERISTICS display."
                ::= { telnetSerialPortEntry 13 }
            
            telnetSerialPortSynchronizeCharacter OBJECT-TYPE
                SYNTAX INTEGER (0..255)
                ACCESS read-write
                STATUS mandatory
                DESCRIPTION
                    "Character input from the character port to cause 
                    sending a synchronization attempt to the remote 
                    partner.  The value 0 indicates no character has 
                    this effect.  Corresponds directly to PORT TELNET 

            
            
                                                               [Page  41]


            
                                  XYPLEX INTERNET MIB        18 Oct 91
            
            
            
                            SYNCHRONIZE and the value labeled 'Synchronize 
                    Character:' in the PORT TELNET CHARACTERISTICS 
                    display."
                ::= { telnetSerialPortEntry 14 }










































            
            
                                                               [Page  42]


            
                                  XYPLEX INTERNET MIB        18 Oct 91
            
            
            
            -- the tn3270 group
            
            -- Implementation of this group is mandatory for all Xyplex
            -- systems that implement tn3270
            
            tn3270DeviceNumber OBJECT-TYPE
                SYNTAX INTEGER
                ACCESS read-only
                STATUS mandatory
                DESCRIPTION
                    "The number of entries in the tn3270 Device table."
                ::= { tn3270 1 }
            
            tn3270LanguageNumber OBJECT-TYPE
                SYNTAX INTEGER
                ACCESS read-only
                STATUS mandatory
                DESCRIPTION
                    "The number of entries in the tn3270 Language 
                    table."
                ::= { tn3270 2 }
            
            tn3270PortKeymapStatus OBJECT-TYPE
                SYNTAX INTEGER { disabled(1), enabled(2) }
                ACCESS read-write
                STATUS mandatory
                DESCRIPTION
                    "Control for individual ports to create their own 
                    keymaps.  Corresponds directly to SERVER TN3270 PORT 
                    KEYMAPS and the value labeled 'Port Keymaps:' in the 
                    SERVER TN3270 display."
                ::= { tn3270 3 }














            
            
                                                               [Page  43]


            
                                  XYPLEX INTERNET MIB        18 Oct 91
            
            
            
            -- The tn3270 Device table
            
            tn3270DeviceTable OBJECT-TYPE
                SYNTAX SEQUENCE OF Tn3270DeviceEntry
                ACCESS not-accessible
                STATUS mandatory
                DESCRIPTION
                    "A list of tn3270 terminal device entries."
                ::= { tn3270 4 }
            
            tn3270DeviceEntry OBJECT-TYPE
                SYNTAX Tn3270DeviceEntry
                ACCESS not-accessible
                STATUS mandatory
                DESCRIPTION
                    "Tn3270 parameter values for a terminal device 
                    entry."
                INDEX { tn3270DeviceName }
                ::= { tn3270DeviceTable 1 }
            
            Tn3270DeviceEntry ::=
                SEQUENCE {
                    tn3270DeviceName
                        DisplayString,
                    tn3270DeviceStatus
                        INTEGER,
                    tn3270DeviceType
                        DisplayString,
                    tn3270Device3278Model
                        INTEGER,
                    tn3270DeviceKeyNumber
                        INTEGER,
                    tn3270DeviceScreenNumber
                        INTEGER
                }
            
            tn3270DeviceName OBJECT-TYPE
                SYNTAX DisplayString (SIZE (1..8))
                ACCESS read-write
                STATUS mandatory
                DESCRIPTION
                    "The name of a generic terminal device.  Corresponds 
                    directly to SERVER TN3270 DEVICE and the value 
                    labeled 'Device Name:' in the SERVER TN3270 DEVICE 
                    display."
                ::= { tn3270DeviceEntry 1 }

            
            
                                                               [Page  44]


            
                                  XYPLEX INTERNET MIB        18 Oct 91
            
            
            
            
            tn3270DeviceStatus OBJECT-TYPE
                SYNTAX INTEGER { invalid(1), valid(2) }
                ACCESS read-write
                STATUS mandatory
                DESCRIPTION
                    "Status of this entry.  Setting the value to 
                    'invalid' invalidates the entry, corresponding 
                    directly to the PURGE SERVER TN3270 DEVICE command.  
                    It is an implementation-specific matter as to 
                    whether the agent removes an invalidated entry from 
                    the table."
                DEFVAL { valid }
                ::= { tn3270DeviceEntry 2 }
            
            tn3270DeviceType OBJECT-TYPE
                SYNTAX DisplayString (SIZE (1..20))
                ACCESS read-write
                STATUS mandatory
                DESCRIPTION
                    "The terminal type character string for use when 
                    tn3270DeviceTn3270Type is insufficient.  Corresponds 
                    directly to SERVER TN3270 DEVICE TERMINALTYPE and 
                    the value labeled 'TerminalType:' in the SERVER 
                    TN3270 DEVICE display."
                ::= { tn3270DeviceEntry 3 }
            
            tn3270Device3278Model OBJECT-TYPE
                SYNTAX INTEGER { model2(1), model5(2) }
                ACCESS read-write
                STATUS mandatory
                DESCRIPTION
                    "The 3278 model for the device.  Corresponds 
                    directly to SERVER TN3270 DEVICE TN3278TYPE and the 
                    value labeled 'Tn3278Type:' in the SERVER TN3270 
                    DEVICE display."
                ::= { tn3270DeviceEntry 4 }
            
            tn3270DeviceKeyNumber OBJECT-TYPE
                SYNTAX INTEGER
                ACCESS read-only
                STATUS mandatory
                DESCRIPTION
                    "The number of Key table entries for this device."
                ::= { tn3270DeviceEntry 5 }
            

            
            
                                                               [Page  45]


            
                                  XYPLEX INTERNET MIB        18 Oct 91
            
            
            
            tn3270DeviceScreenNumber OBJECT-TYPE
                SYNTAX INTEGER
                ACCESS read-only
                STATUS mandatory
                DESCRIPTION
                    "The number of Screen table entries for this 
                    device."
                ::= { tn3270DeviceEntry 6 }






































            
            
                                                               [Page  46]


            
                                  XYPLEX INTERNET MIB        18 Oct 91
            
            
            
            -- The Key table
            
            tn3270KeyTable OBJECT-TYPE
                SYNTAX SEQUENCE OF Tn3270KeyEntry
                ACCESS not-accessible
                STATUS mandatory
                DESCRIPTION
                    "A list of tn3270 key entries by device."
                ::= { tn3270 5 }
            
            tn3270KeyEntry OBJECT-TYPE
                SYNTAX Tn3270KeyEntry
                ACCESS not-accessible
                STATUS mandatory
                DESCRIPTION
                    "Tn3270 parameter values for a key entry for a 
                    device."
                INDEX { tn3270KeyDeviceName, tn3270KeyName }
                ::= { tn3270KeyTable 1 }
            
            Tn3270KeyEntry ::=
                SEQUENCE {
                    tn3270KeyDeviceName
                        DisplayString,
                    tn3270KeyName
                        DisplayString,
                    tn3270KeyStatus
                        INTEGER,
                    tn3270KeyCharacterSequence
                        OCTET STRING,
                    tn3270KeyDescription
                        DisplayString
                }
            
            tn3270KeyDeviceName OBJECT-TYPE
                SYNTAX DisplayString (SIZE (1..8))
                ACCESS read-only
                STATUS mandatory
                DESCRIPTION
                    "The name of a generic terminal device as in 
                    tn3270DeviceName.  Corresponds directly to SERVER 
                    TN3270 DEVICE and the value labeled 'Device Name:' 
                    in the SERVER TN3270 DEVICE display."
                ::= { tn3270KeyEntry 1 }
            
            tn3270KeyName OBJECT-TYPE

            
            
                                                               [Page  47]


            
                                  XYPLEX INTERNET MIB        18 Oct 91
            
            
            
                SYNTAX INTEGER { newline(1), tab(2), backtab(3),
                                 cursorup(4), cursorleft(5),
                                 cursorright(6), cursordown(7),
                                 home(8), delete(9), eraseeof(10),
                                 eraseinput(11), insert(12),
                                 flushinput(13), refresh(14),
                                 centsign(15), duplicate(16),
                                 fieldmark(17), scroll(18),
                                 status(19), reset(20),
                                 fastleft(21), fastright(22),
                                 showkeys(23), print(24),
                                 pf1(39), pf2(40), pf3(41),
                                 pf4(42), pf5(43), pf6(44),
                                 pf7(45), pf8(46), pf9(47), pf10(48),
                                 pf11(49), pf12(50), pf13(51),
                                 pf14(52), pf15(53), pf16(54),
                                 pf17(55), pf18(56), pf19(57),
                                 pf20(58), pf21(59), pf22(60),
                                 pf23(61), pf24(62), pa1(63),
                                 pa2(64), pa3(65), sysreq(66),
                                 enter(67), clear(68), cursorsel(69),
                                 test(70) }
                ACCESS read-only
                STATUS mandatory
                DESCRIPTION
                    "The key name to which this entry applies.  
                    Corresponds directly to the key portion of SERVER 
                    TN3270 DEVICE KEYMAP and the value labeled 
                    '3270-key' in the 'Keymap:' section of the SERVER 
                    TN3270 DEVICE display."
                ::= { tn3270KeyEntry 2 }
            
            tn3270KeyStatus OBJECT-TYPE
                SYNTAX INTEGER { invalid(1), valid(2) }
                ACCESS read-write
                STATUS mandatory
                DESCRIPTION
                    "Status of this entry.  Setting the value to 
                    'invalid' invalidates the entry.  It is an 
                    implementation-specific matter as to whether the 
                    agent removes an invalidated entry from the table."
                DEFVAL { valid }
                ::= { tn3270KeyEntry 3 }
            
            tn3270KeyCharacterSequence OBJECT-TYPE
                SYNTAX OCTET STRING (SIZE (0..8))

            
            
                                                               [Page  48]


            
                                  XYPLEX INTERNET MIB        18 Oct 91
            
            
            
                ACCESS read-write
                STATUS mandatory
                DESCRIPTION
                    "The ASCII character sequence for the key.  
                    Corresponds directly to the escape-sequence portion 
                    of SERVER TN3270 DEVICE KEYMAP and the value labeled 
                    'KeyCode' in the 'Keymap:' section of the SERVER 
                    TN3270 DEVICE display."
                ::= { tn3270KeyEntry 4 }
            
            tn3270KeyDescription OBJECT-TYPE
                SYNTAX DisplayString (SIZE (0..5))
                ACCESS read-write
                STATUS mandatory
                DESCRIPTION
                    "Descriptive text for the key.  Corresponds directly 
                    to the description portion of SERVER TN3270 DEVICE 
                    KEYMAP and the value labeled 'Description' in the 
                    SERVER TN3270 DEVICE display."
                ::= { tn3270KeyEntry 5 }
            

























            
            
                                                               [Page  49]


            
                                  XYPLEX INTERNET MIB        18 Oct 91
            
            
            
            -- The Screen Action table
            
            tn3270ScreenTable OBJECT-TYPE
                SYNTAX SEQUENCE OF Tn3270ScreenEntry
                ACCESS not-accessible
                STATUS mandatory
                DESCRIPTION
                    "A list of tn3270 screen action entries by device."
                ::= { tn3270 6 }
            
            tn3270ScreenEntry OBJECT-TYPE
                SYNTAX Tn3270ScreenEntry
                ACCESS not-accessible
                STATUS mandatory
                DESCRIPTION
                    "Tn3270 parameter values for a screen action entry 
                    for a device."
                INDEX { tn3270ScreenDeviceName, tn3270ScreenActionName }
                ::= { tn3270ScreenTable 1 }
            
            Tn3270ScreenEntry ::=
                SEQUENCE {
                    tn3270ScreenDeviceName
                        DisplayString,
                    tn3270ScreenActionName
                        INTEGER,
                    tn3270ScreenStatus
                        INTEGER,
                    tn3270ScreenCharacterSequence
                        OCTET STRING
                }
            
            tn3270ScreenDeviceName OBJECT-TYPE
                SYNTAX DisplayString (SIZE (1..8))
                ACCESS read-only
                STATUS mandatory
                DESCRIPTION
                    "The name of a generic terminal device as in 
                    tn3270DeviceName.  Corresponds directly to SERVER 
                    TN3270 DEVICE and the value labeled 'Device Name:' 
                    in the SERVER TN3270 DEVICE display."
                ::= { tn3270ScreenEntry 1 }
            
            tn3270ScreenActionName OBJECT-TYPE
                SYNTAX INTEGER { eraseeol(1), clearscr(2),
                                 movecursor(3), col132(4), col80(5),

            
            
                                                               [Page  50]


            
                                  XYPLEX INTERNET MIB        18 Oct 91
            
            
            
                                 beep(6), charset(7), boldon(8),
                                 boldoff(9), blinkon(10),
                                 blinkoff(11), underscoreon(12),
                                 underscoreoff(13), reverseon(14),
                                 reverseoff(15),
                                 status1(26), status2(27),
                                 reset1(28), reset2(29),
                                 reset3(30), reset4(31),
                                 base(32), sgr(33) }
                ACCESS read-only
                STATUS mandatory
                DESCRIPTION
                    "The screen action to which this entry applies.  
                    Corresponds directly to the action portion of SERVER 
                    TN3270 DEVICE SCREENMAP and the value labeled 
                    'Terminal Function' in the 'Screenmap: section of 
                    the SERVER TN3270 DEVICE display."
                ::= { tn3270ScreenEntry 2 }
            
            tn3270ScreenStatus OBJECT-TYPE
                SYNTAX INTEGER { invalid(1), valid(2) }
                ACCESS read-write
                STATUS mandatory
                DESCRIPTION
                    "Status of this entry.  Setting the value to 
                    'invalid' invalidates the entry.  It is an 
                    implementation-specific matter as to whether the 
                    agent removes an invalidated entry from the table."
                DEFVAL { valid }
                ::= { tn3270ScreenEntry 3 }
            
            tn3270ScreenCharacterSequence OBJECT-TYPE
                SYNTAX OCTET STRING (SIZE (0..15))
                ACCESS read-write
                STATUS mandatory
                DESCRIPTION
                    "The ASCII character sequence for the screen action.  
                    Some actions may have a lesser length limit.  
                    Corresponds directly to the escape-sequence portion 
                    of SERVER TN3270 DEVICE SCREENMAP and the value 
                    labeled 'HexCode' in the 'Screenmap: section of the 
                    SERVER TN3270 DEVICE display."
                ::= { tn3270ScreenEntry 4 }
            


            
            
                                                               [Page  51]


            
                                  XYPLEX INTERNET MIB        18 Oct 91
            
            
            
            -- The Language table
            
            tn3270LanguageTable OBJECT-TYPE
                SYNTAX SEQUENCE OF Tn3270LanguageEntry
                ACCESS not-accessible
                STATUS mandatory
                DESCRIPTION
                    "A list of tn3270 language entries."
                ::= { tn3270 7 }
            
            tn3270LanguageEntry OBJECT-TYPE
                SYNTAX Tn3270LanguageEntry
                ACCESS not-accessible
                STATUS mandatory
                DESCRIPTION
                    "Tn3270 parameter values for a language entry."
                INDEX { tn3270LanguageName }
                ::= { tn3270LanguageTable 1 }
            
            Tn3270LanguageEntry ::=
                SEQUENCE {
                    tn3270LanguageName
                        DisplayString,
                    tn3270LanguageStatus
                        INTEGER
                }
            
            tn3270LanguageName OBJECT-TYPE
                SYNTAX DisplayString (SIZE (1..8))
                ACCESS read-write
                STATUS mandatory
                DESCRIPTION
                    "The name of language for character translation 
                    tables.  Corresponds directly to SERVER TN3270 
                    LANGUAGE and the value labeled 'Language Name:' in 
                    the SERVER LANGUAGE display."
                ::= { tn3270LanguageEntry 1 }
            
            tn3270LanguageStatus OBJECT-TYPE
                SYNTAX INTEGER { invalid(1), valid(2) }
                ACCESS read-write
                STATUS mandatory
                DESCRIPTION
                    "Status of this entry.  Setting the value to 
                    'invalid' invalidates the entry.  It is an 
                    implementation-specific matter as to whether the 

            
            
                                                               [Page  52]


            
                                  XYPLEX INTERNET MIB        18 Oct 91
            
            
            
                            agent removes an invalidated entry from the table."
                DEFVAL { valid }
                ::= { tn3270LanguageEntry 2 }
            










































            
            
                                                               [Page  53]


            
                                  XYPLEX INTERNET MIB        18 Oct 91
            
            
            
            -- The Language EBCDIC to ASCII table
            
            eToALanguageTable OBJECT-TYPE
                SYNTAX SEQUENCE OF EToALanguageEntry
                ACCESS not-accessible
                STATUS mandatory
                DESCRIPTION
                    "A list of language EBCDIC to ASCII conversion 
                    entries."
                ::= { tn3270 8 }
            
            eToALanguageEntry OBJECT-TYPE
                SYNTAX EToALanguageEntry
                ACCESS not-accessible
                STATUS mandatory
                DESCRIPTION
                    "EBCDIC to ASCII parameter values for a language 
                    entry."
                INDEX { eToALanguageName, eToAOffset }
                ::= { eToALanguageTable 1 }
            
            EToALanguageEntry ::=
                SEQUENCE {
                    eToALanguageName
                        DisplayString,
                    eToAOffset
                        INTEGER,
                    eToAValue
                        INTEGER
                }
            
            eToALanguageName OBJECT-TYPE
                SYNTAX DisplayString (SIZE (1..8))
                ACCESS read-only
                STATUS mandatory
                DESCRIPTION
                    "The name of language from the language table."
                ::= { eToALanguageEntry 1 }
            
            eToAOffset OBJECT-TYPE
                SYNTAX INTEGER (65..256)
                ACCESS read-only
                STATUS mandatory
                DESCRIPTION
                    "EBCDIC character offset plus one, that is, the 
                    value 1 corresponds to an operational offset of 0.  

            
            
                                                               [Page  54]


            
                                  XYPLEX INTERNET MIB        18 Oct 91
            
            
            
                            Corresponds directly to the offset portion of SERVER 
                    TN3270 LANGUAGE and the hexadecimal labels around 
                    the conversion table labeled 'EBCDIC to ASCII' in 
                    the SERVER LANGUAGE display."
                ::= { eToALanguageEntry 2 }
            
            eToAValue OBJECT-TYPE
                SYNTAX INTEGER (32..255)
                ACCESS read-write
                STATUS mandatory
                DESCRIPTION
                    "ASCII character value for the EBCDIC offset.  
                    Corresponds directly to the value portion of SERVER 
                    TN3270 LANGUAGE and the values in the conversion 
                    table labeled 'EBCDIC to ASCII' in the SERVER 
                    LANGUAGE display."
                ::= { eToALanguageEntry 3 }
            




























            
            
                                                               [Page  55]


            
                                  XYPLEX INTERNET MIB        18 Oct 91
            
            
            
            -- The Language ASCII to EBCDIC table
            
            aToELanguageTable OBJECT-TYPE
                SYNTAX SEQUENCE OF AToELanguageEntry
                ACCESS not-accessible
                STATUS mandatory
                DESCRIPTION
                    "A list of language ASCII to EBCDIC conversion 
                    entries."
                ::= { tn3270 9 }
            
            aToELanguageEntry OBJECT-TYPE
                SYNTAX AToELanguageEntry
                ACCESS not-accessible
                STATUS mandatory
                DESCRIPTION
                    "ASCII to EBCDIC parameter values for a language 
                    entry."
                INDEX { aToELanguageName, aToEOffset }
                ::= { aToELanguageTable 1 }
            
            AToELanguageEntry ::=
                SEQUENCE {
                    aToELanguageName
                        DisplayString,
                    aToEOffset
                        INTEGER,
                    aToEValue
                        INTEGER
                }
            
            aToELanguageName OBJECT-TYPE
                SYNTAX DisplayString (SIZE (1..8))
                ACCESS read-only
                STATUS mandatory
                DESCRIPTION
                    "The name of language from the language table."
                ::= { aToELanguageEntry 1 }
            
            aToEOffset OBJECT-TYPE
                SYNTAX INTEGER (33..256)
                ACCESS read-only
                STATUS mandatory
                DESCRIPTION
                    "ASCII character offset plus one, that is, the value 
                    1 corresponds to an operational offset of 0.  

            
            
                                                               [Page  56]


            
                                  XYPLEX INTERNET MIB        18 Oct 91
            
            
            
                            Corresponds directly to the offset portion of SERVER 
                    TN3270 LANGUAGE and the hexadecimal labels around 
                    the conversion table labeled 'ASCII to EBCDIC' in 
                    the SERVER LANGUAGE display."
                ::= { aToELanguageEntry 2 }
            
            aToEValue OBJECT-TYPE
                SYNTAX INTEGER (64..255)
                ACCESS read-write
                STATUS mandatory
                DESCRIPTION
                    "EBCDIC character value for the ASCII offset.  
                    Corresponds directly to the value portion of SERVER 
                    TN3270 LANGUAGE and the values in the conversion 
                    table labeled 'ASCII to EBCDIC' in the SERVER 
                    LANGUAGE display."
                ::= { aToELanguageEntry 3 }
            




























            
            
                                                               [Page  57]


            
                                  XYPLEX INTERNET MIB        18 Oct 91
            
            
            
            -- the tn3270 Port table
            
            tn3270PortTable OBJECT-TYPE
                SYNTAX SEQUENCE OF Tn3270PortEntry
                ACCESS not-accessible
                STATUS mandatory
                DESCRIPTION
                    "A list of tn3270 character port entries."
                ::= { tn3270 10 }
            
            tn3270PortEntry OBJECT-TYPE
                SYNTAX Tn3270PortEntry
                ACCESS not-accessible
                STATUS mandatory
                DESCRIPTION
                    "Parameter values for a tn3270 port."
                INDEX { tn3270PortIndex }
                ::= { tn3270PortTable 1 }
            
            Tn3270PortEntry ::=
                SEQUENCE {
                    tn3270PortIndex
                        INTEGER,
                    tn3270PortDeviceName
                        DisplayString,
                    tn3270PortLanguageName
                        DisplayString,
                    tn3270PortExtendedAttributes
                        INTEGER,
                    tn3270PortEorNegotiation
                        INTEGER,
                    tn3270PortErrorLock
                        INTEGER
                }
            
            tn3270PortIndex OBJECT-TYPE
                SYNTAX INTEGER
                ACCESS read-only
                STATUS mandatory
                DESCRIPTION
                    "An index value that uniquely identifies a port.  
                    The port identified by a particular value of this 
                    index is the same port as identified by 
                    charPortIndex in the Character MIB [11]."
                ::= { tn3270PortEntry 1 }
            

            
            
                                                               [Page  58]


            
                                  XYPLEX INTERNET MIB        18 Oct 91
            
            
            
            tn3270PortDeviceName OBJECT-TYPE
                SYNTAX DisplayString (SIZE (1..8))
                ACCESS read-write
                STATUS mandatory
                DESCRIPTION
                    "The name of a generic terminal device from the 
                    tn3270 device table.  Corresponds directly to PORT 
                    TELNET TN3270 DEVICE and the value labeled 'Tn3270 
                    Device:' in the PORT TELNET display."
                ::= { tn3270PortEntry 2 }
            
            tn3270PortLanguageName OBJECT-TYPE
                SYNTAX DisplayString (SIZE (1..8))
                ACCESS read-write
                STATUS mandatory
                DESCRIPTION
                    "The name of language from the tn3270 language 
                    table.  Corresponds directly to PORT TELNET TN3270 
                    LANGUAGE and the value labeled 'Tn3270 Language:' in 
                    the PORT TELNET display."
                ::= { tn3270PortEntry 3 }
            
            tn3270PortExtendedAttributes OBJECT-TYPE
                SYNTAX INTEGER { disabled(1), enabled(2) }
                ACCESS read-write
                STATUS mandatory
                DESCRIPTION
                    "A control indicating that certain 3270 extended 
                    attributes are supported on the port.  Corresponds 
                    directly to PORT TELNET TN3270 XTDATTRS and the 
                    label 'Tn3270 XtdAttrs' following the label 'Enabled 
                    Characteristics' in the PORT TELNET display."
                ::= { tn3270PortEntry 4 }
            
            tn3270PortEorNegotiation OBJECT-TYPE
                SYNTAX INTEGER { disabled(1), enabled(2) }
                ACCESS read-write
                STATUS mandatory
                DESCRIPTION
                    "A control for negotiation of the Telnet EOR option 
                    when establishing a tn3270 session on the port.  
                    Corresponds directly to PORT TELNET TN3270 EOR and 
                    the label 'Tn3270 EOR' following the label 'Enabled 
                    Characteristics' in the PORT TELNET display."
                ::= { tn3270PortEntry 5 }
            

            
            
                                                               [Page  59]


            
                                  XYPLEX INTERNET MIB        18 Oct 91
            
            
            
            tn3270PortErrorLock OBJECT-TYPE
                SYNTAX INTEGER { disabled(1), enabled(2) }
                ACCESS read-write
                STATUS mandatory
                DESCRIPTION
                    "A control for requiring use the RESET key when the 
                    host reports an error during a tn3270 session on the 
                    port.  Corresponds directly to PORT TELNET TN3270 
                    ERRORLOCK and the label 'Tn3270 ErrorLock' following 
                    the label 'Enabled Characteristics' in the PORT 
                    TELNET display."
                ::= { tn3270PortEntry 6 }


































            
            
                                                               [Page  60]


            
                                  XYPLEX INTERNET MIB        18 Oct 91
            
            
            
            -- the Kerberos group
            
            -- Implementation of this group is mandatory for all Xyplex
            -- systems that implement a Kerberos client
            
            kerbStatus OBJECT-TYPE
                SYNTAX INTEGER { none(1), login(2) }
                ACCESS read-write
                STATUS mandatory
                DESCRIPTION
                    "A control indicating the level of Kerberos 
                    operation on the system.  Corresponds directly to 
                    SERVER KERBEROS STATUS and the value labeled 
                    'Kerberos Security:' in the SERVER KERBEROS 
                    display."
                ::= { kerberos 1 }
            
            kerbRealm OBJECT-TYPE
                SYNTAX DisplayString (SIZE (0..40))
                ACCESS read-write
                STATUS mandatory
                DESCRIPTION
                    "The Kerberos realm with which the kerbServerName1 
                    and kerbServerName2 are associated.  Corresponds 
                    directly to SERVER KERBEROS REALM and the value 
                    labeled 'Kerberos Realm:' in the SERVER KERBEROS 
                    display."
                ::= { kerberos 2 }
            
            kerbQueryLimit OBJECT-TYPE
                SYNTAX INTEGER (1..16)
                ACCESS read-write
                STATUS mandatory
                DESCRIPTION
                    "The maximum number of attempts the system can make 
                    when trying to verify a Kerberos ID.  Corresponds 
                    directly to SERVER KERBEROS QUERY LIMIT and the 
                    value labeled 'Kerberos Query Limit:' in the SERVER 
                    KERBEROS display."
                ::= { kerberos 3 }
            
            kerbMasterName OBJECT-TYPE
                SYNTAX DisplayString (SIZE (0..50))
                ACCESS read-write
                STATUS mandatory
                DESCRIPTION

            
            
                                                               [Page  61]


            
                                  XYPLEX INTERNET MIB        18 Oct 91
            
            
            
                    "The Domain name of the Kerberos master host system, 
                    which holds the Kerberos database.  Corresponds 
                    directly to SERVER KERBEROS MASTER and the value 
                    labeled 'Kerberos Master:' in the SERVER KERBEROS 
                    display."
                ::= { kerberos 4 }
            
            kerbServerName1 OBJECT-TYPE
                SYNTAX DisplayString (SIZE (0..50))
                ACCESS read-write
                STATUS mandatory
                DESCRIPTION
                    "The Domain name of the first Kerberos server to try 
                    when the system verifys a Kerberos ID.  Corresponds 
                    directly to SERVER KERBEROS PRIMARY SERVER and the 
                    value labeled 'Kerberos Primary Server:' in the 
                    SERVER KERBEROS display."
                ::= { kerberos 5 }
            
            kerbServerName2 OBJECT-TYPE
                SYNTAX DisplayString (SIZE (0..50))
                ACCESS read-write
                STATUS mandatory
                DESCRIPTION
                    "The Domain name of the Kerberos server to try when 
                    the system verifys a Kerberos ID and cannot reach 
                    the Kerberos primary server.  Corresponds directly 
                    to SERVER KERBEROS SECONDARY SERVER and the value 
                    labeled 'Kerberos Secondary Server:' in the SERVER 
                    KERBEROS display."
                ::= { kerberos 6 }
            
            kerbInsecureLogins OBJECT-TYPE
                SYNTAX Counter
                ACCESS read-only
                STATUS mandatory
                DESCRIPTION
                    "The number of user logins on ports for which 
                    Kerberos user verification is not enabled.  
                    Corresponds directly to the value labeled 'Logins 
                    without Kerberos:' in the SERVER KERBEROS display."
                ::= { kerberos 7 }
            
            kerbSecureLogins OBJECT-TYPE
                SYNTAX Counter
                ACCESS read-only

            
            
                                                               [Page  62]


            
                                  XYPLEX INTERNET MIB        18 Oct 91
            
            
            
                STATUS mandatory
                DESCRIPTION
                    "The number of successful user logins on ports for 
                    which Kerberos user verification is enabled.  
                    Corresponds directly to the value labeled 
                    'Successful Logins:' in the SERVER KERBEROS 
                    display."
                ::= { kerberos 8 }
            
            kerbSecureLoginsFailed OBJECT-TYPE
                SYNTAX Counter
                ACCESS read-only
                STATUS mandatory
                DESCRIPTION
                    "The number of verification failures due to 
                    incorrect ID or password for attempted user logins 
                    on ports for which Kerberos user verification is 
                    enabled.  Corresponds directly to the value labeled 
                    'Unsuccessful Logins:' in the SERVER KERBEROS 
                    display."
                ::= { kerberos 9 }
            
            kerbPasswordChangeFailed OBJECT-TYPE
                SYNTAX Counter
                ACCESS read-only
                STATUS mandatory
                DESCRIPTION
                    "The number of user failures to change their 
                    Kerberos password due to invalid old password or new 
                    password verification.  Corresponds directly to the 
                    value labeled 'Password Change Failures:' in the 
                    SERVER KERBEROS display."
                ::= { kerberos 10 }
            
            kerbError OBJECT-TYPE
                SYNTAX INTEGER
                ACCESS read-only
                STATUS mandatory
                DESCRIPTION
                    "The error number of the most recent 
                    Kerberos-related failure.  Corresponds directly to 
                    the value labeled 'Last Kerberos Error:' in the 
                    SERVER KERBEROS display.  For a list of error 
                    numbers and their meanings, consult relevant Xyplex 
                    or Kerberos documentation."
                ::= { kerberos 11 }

            
            
                                                               [Page  63]


            
                                  XYPLEX INTERNET MIB        18 Oct 91
            
            
            
            
            kerbErrorTime OBJECT-TYPE
                SYNTAX DateTime
                ACCESS read-only
                STATUS mandatory
                DESCRIPTION
                    "The date and time that kerbError was last updated.  
                    Corresponds directly to the value labeled 
                    'Occurred:' in the SERVER KERBEROS display."
                ::= { kerberos 12 }
            
            kerbMasterAccess OBJECT-TYPE
                SYNTAX Counter
                ACCESS read-only
                STATUS mandatory
                DESCRIPTION
                    "The number of times the system successfully 
                    accessed the Kerberos master host.  Corresponds 
                    directly to the value labeled 'Attempts to access:', 
                    'Master', and 'Successful:' in the SERVER KERBEROS 
                    display."
                ::= { kerberos 13 }
            
            kerbMasterAccessFailed OBJECT-TYPE
                SYNTAX Counter
                ACCESS read-only
                STATUS mandatory
                DESCRIPTION
                    "The number of times the system failed access to the 
                    Kerberos master host.  Corresponds directly to the 
                    value labeled 'Attempts to access:', 'Master', and 
                    'Unsuccessful:' in the SERVER KERBEROS display."
                ::= { kerberos 14 }
            
            kerbServerAccess1 OBJECT-TYPE
                SYNTAX Counter
                ACCESS read-only
                STATUS mandatory
                DESCRIPTION
                    "The number of times the system successfully 
                    accessed the Kerberos primary server.  Corresponds 
                    directly to the value labeled 'Attempts to access:', 
                    'Server1', and 'Successful:' in the SERVER KERBEROS 
                    display."
                ::= { kerberos 15 }
            

            
            
                                                               [Page  64]


            
                                  XYPLEX INTERNET MIB        18 Oct 91
            
            
            
            kerbServerAccessFailed1 OBJECT-TYPE
                SYNTAX Counter
                ACCESS read-only
                STATUS mandatory
                DESCRIPTION
                    "The number of times the system failed access to the 
                    Kerberos primary server.  Corresponds directly to 
                    the value labeled 'Attempts to access:', 'Server1', 
                    and 'Unsuccessful:' in the SERVER KERBEROS 
                    display."
                ::= { kerberos 16 }
            
            kerbServerAccess2 OBJECT-TYPE
                SYNTAX Counter
                ACCESS read-only
                STATUS mandatory
                DESCRIPTION
                    "The number of times the system successfully 
                    accessed the Kerberos secondary server.  Corresponds 
                    directly to the value labeled 'Attempts to access:', 
                    'Server2', and 'Successful:' in the SERVER KERBEROS 
                    display."
                ::= { kerberos 17 }
            
            kerbServerAccessFailed2 OBJECT-TYPE
                SYNTAX Counter
                ACCESS read-only
                STATUS mandatory
                DESCRIPTION
                    "The number of times the system failed access to the 
                    Kerberos secondary server.  Corresponds directly to 
                    the value labeled 'Attempts to access:', 'Server2', 
                    and 'Unsuccessful:' in the SERVER KERBEROS 
                    display."
                ::= { kerberos 18 }











            
            
                                                               [Page  65]


            
                                  XYPLEX INTERNET MIB        18 Oct 91
            
            
            
            -- the Kerberos Port table
            
            kerbPortTable OBJECT-TYPE
                SYNTAX SEQUENCE OF KerbPortEntry
                ACCESS not-accessible
                STATUS mandatory
                DESCRIPTION
                    "A list of Kerberos character port entries."
                ::= { kerberos 19 }
            
            kerbPortEntry OBJECT-TYPE
                SYNTAX KerbPortEntry
                ACCESS not-accessible
                STATUS mandatory
                DESCRIPTION
                    "Parameter values for a Kerberos port."
                INDEX { kerbPortIndex }
                ::= { kerbPortTable 1 }
            
            KerbPortEntry ::=
                SEQUENCE {
                    kerbPortIndex
                        INTEGER,
                    kerbPortStatus
                        INTEGER
                }
            
            kerbPortIndex OBJECT-TYPE
                SYNTAX INTEGER
                ACCESS read-only
                STATUS mandatory
                DESCRIPTION
                    "An index value that uniquely identifies a port 
                    could relate to Kerberos.  The port identified by a 
                    particular value of this index is the same port as 
                    identified by charPortIndex in the Character 
                    MIB [11]."
                ::= { kerbPortEntry 1 }
            
            kerbPortStatus OBJECT-TYPE
                SYNTAX INTEGER { none(1), login(2) }
                ACCESS read-write
                STATUS mandatory
                DESCRIPTION
                    "A control indicating the level of Kerberos 
                    operation on the port.  Corresponds directly to PORT 

            
            
                                                               [Page  66]


            
                                  XYPLEX INTERNET MIB        18 Oct 91
            
            
            
                            KERBEROS and the value 'Kerberos' following the 
                    label 'Enabled Characteristics' in the PORT 
                    CHARACTERISTICS display."
                ::= { kerbPortEntry 2 }










































            
            
                                                               [Page  67]


            
                                  XYPLEX INTERNET MIB        18 Oct 91
            
            
            
            -- the Port Security group
            
            -- Implementation of this group is mandatory for all Xyplex
            -- systems that implement Internet port security
            
            psEntryNumber OBJECT-TYPE
                SYNTAX INTEGER
                ACCESS read-only
                STATUS mandatory
                DESCRIPTION
                    "The number of security entries in this system's 
                    port security table with psEntryStatus of 'valid'."
                ::= { portSecurity 1 }
            
            psEntryNumberLimit OBJECT-TYPE
                SYNTAX INTEGER
                ACCESS read-only
                STATUS mandatory
                DESCRIPTION
                    "The maximum number of security entries in this 
                    system's port security table."
                ::= { portSecurity 2 }
            
            psEntryInvalidIndex OBJECT-TYPE
                SYNTAX INTEGER
                ACCESS read-only
                STATUS mandatory
                DESCRIPTION
                    "A value of psEntryIndex for an entry that has 
                    psEntryStatus of 'invalid'.  A management station 
                    may choose this value when adding a new entry.  
                    Collisions between independent management stations 
                    simultaneously using the same number are beyond the 
                    scope of this document."
                ::= { portSecurity 3 }











            
            
                                                               [Page  68]


            
                                  XYPLEX INTERNET MIB        18 Oct 91
            
            
            
            -- the Port Security table
            
            psPortTable OBJECT-TYPE
                SYNTAX SEQUENCE OF PsPortEntry
                ACCESS not-accessible
                STATUS mandatory
                DESCRIPTION
                    "A list of port security character port entries."
                ::= { portSecurity 4 }
            
            psPortEntry OBJECT-TYPE
                SYNTAX PsPortEntry
                ACCESS not-accessible
                STATUS mandatory
                DESCRIPTION
                    "Port security parameter values for a port."
                INDEX { psPortIndex }
                ::= { psPortTable 1 }
            
            PsPortEntry ::=
                SEQUENCE {
                    psPortIndex
                        INTEGER,
                    psPortDefaultInboundAccess
                        INTEGER,
                    psPortDefaultOutboundAccess
                        INTEGER
                }
            
            psPortIndex OBJECT-TYPE
                SYNTAX INTEGER
                ACCESS read-only
                STATUS mandatory
                DESCRIPTION
                    "An index value that uniquely identifies a port for 
                    security purposes.  The port identified by a 
                    particular value of this index is the same port as 
                    identified by charPortIndex in the Character MIB 
                    [11]."
                ::= { psPortEntry 1 }
            
            psPortDefaultInboundAccess OBJECT-TYPE
                SYNTAX INTEGER { allow(1), deny(2) }
                ACCESS read-write
                STATUS mandatory
                DESCRIPTION

            
            
                                                               [Page  69]


            
                                  XYPLEX INTERNET MIB        18 Oct 91
            
            
            
                    "The default access to the port for incoming TCP 
                    connections.  Corresponds directly to PORT INTERNET 
                    SECURITY DEFAULT INBOUND and the value labeled 
                    'Inbound Default:' in the PORT INTERNET SECURITY 
                    display."
                ::= { psPortEntry 2 }
            
            psPortDefaultOutboundAccess OBJECT-TYPE
                SYNTAX INTEGER { allow(1), deny(2) }
                ACCESS read-write
                STATUS mandatory
                DESCRIPTION
                    "The default access to the port for outgoing TCP 
                    connections.  Corresponds directly to PORT INTERNET 
                    SECURITY DEFAULT OUTBOUND and the value labeled 
                    'Outbound Default:' in the PORT INTERNET SECURITY 
                    display."
                ::= { psPortEntry 3 }




























            
            
                                                               [Page  70]


            
                                  XYPLEX INTERNET MIB        18 Oct 91
            
            
            
            -- the Port Security table
            
            psTable OBJECT-TYPE
                SYNTAX SEQUENCE OF PsEntry
                ACCESS not-accessible
                STATUS mandatory
                DESCRIPTION
                    "A list of port security entries."
                ::= { portSecurity 5 }
            
            psEntry OBJECT-TYPE
                SYNTAX PsEntry
                ACCESS not-accessible
                STATUS mandatory
                DESCRIPTION
                    "Port security parameter values for an entry for a 
                    port."
                INDEX { psEntryIndex }
                ::= { psTable 1 }
            
            PsEntry ::=
                SEQUENCE {
                    psEntryIndex
                        INTEGER,
                    psEntryStatus
                        INTEGER,
                    psEntryAddress
                        IpAddress,
                    psEntryMask
                        IpAddress,
                    psEntryAccess
                        INTEGER,
                    psEntryDirection
                        INTEGER,
                    psEntryPortMap
                        OCTET STRING
                }
            
            psEntryIndex OBJECT-TYPE
                SYNTAX INTEGER
                ACCESS read-only
                STATUS mandatory
                DESCRIPTION
                    "A small, numeric distinguisher for port security 
                    entries.  When adding a new entry, the client should 
                    specify an unused value, such as 

            
            
                                                               [Page  71]


            
                                  XYPLEX INTERNET MIB        18 Oct 91
            
            
            
                            psEntryInvalidIndex.  Corresponds directly to the 
                    value labeled 'Entry' in the SERVER INTERNET 
                    SECURITY display."
                ::= { psEntry 1 }
            
            psEntryStatus OBJECT-TYPE
                SYNTAX INTEGER { invalid(1), valid(2) }
                ACCESS read-write
                STATUS mandatory
                DESCRIPTION
                    "Status of this entry.  Setting the value to 
                    'invalid' invalidates the entry, corresponding 
                    directly to the CLEAR INTERNET SECURITY command.  It 
                    is an implementation-specific matter as to whether 
                    the agent removes an invalidated entry from the 
                    table.  When creating a new instance, 
                    psEntryAddress, psEntryMask, psEntryAccess, and 
                    psEntryDirection for the new instance must be 
                    present in the set request."
                DEFVAL { valid }
                ::= { psEntry 2 }
            
            psEntryAddress OBJECT-TYPE
                SYNTAX IpAddress
                ACCESS read-write
                STATUS mandatory
                DESCRIPTION
                    "The IP address to which the entry pertains.  
                    Corresponds directly to the PORT INTERNET SECURITY 
                    internet address and the value labeled 'Internet 
                    Address' in the SERVER INTERNET SECURITY display."
                ::= { psEntry 3 }
            
            psEntryMask OBJECT-TYPE
                SYNTAX IpAddress
                ACCESS read-write
                STATUS mandatory
                DESCRIPTION
                    "The mask applied to psEntryAddress when making a 
                    security check based on this entry.  Corresponds 
                    directly to PORT INTERNET SECURITY MASK and the 
                    value labeled 'Security Mask' in the SERVER INTERNET 
                    SECURITY display."
                ::= { psEntry 4 }
            
            psEntryAccess OBJECT-TYPE

            
            
                                                               [Page  72]


            
                                  XYPLEX INTERNET MIB        18 Oct 91
            
            
            
                SYNTAX INTEGER { allow(1), deny(2) }
                ACCESS read-write
                STATUS mandatory
                DESCRIPTION
                    "The access to the port for TCP connections when 
                    making a security check based on this entry.  
                    Corresponds directly to PORT INTERNET SECURITY ALLOW 
                    or DENY and the value labeled 'Access' in the SERVER 
                    INTERNET SECURITY display."
                ::= { psEntry 5 }
            
            psEntryDirection OBJECT-TYPE
                SYNTAX INTEGER { inbound(1), outbound(2) }
                ACCESS read-write
                STATUS mandatory
                DESCRIPTION
                    "The direction of TCP connections to which this 
                    entry applies.  Corresponds directly to PORT 
                    INTERNET SECURITY INBOUND or OUTBOUND and the value 
                    labeled 'Direction' in the SERVER INTERNET SECURITY 
                    display."
                ::= { psEntry 6 }
            
            psEntryPortMap OBJECT-TYPE
                SYNTAX OCTET STRING
                ACCESS read-write
                STATUS mandatory
                DESCRIPTION
                    "The list of character ports to which this entry 
                    applies.  The OCTET STRING contains a bitmap, with 
                    one bit for each port, and enough octets for all the 
                    ports on the system.  Port numbers are as defined 
                    for charPortIndex in the Character MIB [11].  
                    Corresponding bit numbers start with 1 as the 
                    high-order bit of the first octet.  Corresponds 
                    directly to PORT INTERNET SECURITY and the value 
                    labeled 'Ports' in the SERVER INTERNET SECURITY 
                    display."
                ::= { psEntry 7 }







            
            
                                                               [Page  73]


            
                                  XYPLEX INTERNET MIB        18 Oct 91
            
            
            
            -- the XREMOTE group
            
            -- Implementation of this group is mandatory for all Xyplex
            -- systems that implement XREMOTE
            
            xremoteServerName1 OBJECT-TYPE
                SYNTAX DisplayString (SIZE (0..50))
                ACCESS read-write
                STATUS mandatory
                DESCRIPTION
                    "The Domain name of the first XREMOTE font server to 
                    try for downloading fonts.  Corresponds directly to 
                    SERVER XREMOTE PRIMARY SERVER and the value labeled 
                    'Xremote Primary Font Server:' in the SERVER XREMOTE 
                    display."
                ::= { xremote 1 }
            
            xremoteServerName2 OBJECT-TYPE
                SYNTAX DisplayString (SIZE (0..50))
                ACCESS read-write
                STATUS mandatory
                DESCRIPTION
                    "The Domain name of the XREMOTE font server to try 
                    for downloading fonts and the primary font server 
                    does not respond.  Corresponds directly to SERVER 
                    XREMOTE SECONDARY SERVER and the value labeled 
                    'Xremote Secondary Font Server:' in the SERVER 
                    XREMOTE display."
                ::= { xremote 2 }
            
            xremoteServerAccess1 OBJECT-TYPE
                SYNTAX Counter
                ACCESS read-only
                STATUS mandatory
                DESCRIPTION
                    "The number of times the system successfully 
                    accessed the XREMOTE primary font server.  
                    Corresponds directly to the value labeled 'Attempts 
                    to access:', 'Server1', and 'Successful:' in the 
                    SERVER XREMOTE display."
                ::= { xremote 3 }
            
            xremoteServerAccessFailed1 OBJECT-TYPE
                SYNTAX Counter
                ACCESS read-only
                STATUS mandatory

            
            
                                                               [Page  74]


            
                                  XYPLEX INTERNET MIB        18 Oct 91
            
            
            
                DESCRIPTION
                    "The number of times the system failed access to the 
                    XREMOTE primary font server.  Corresponds directly 
                    to the value labeled 'Attempts to access:', 
                    'Server1', and 'Unsuccessful:' in the SERVER XREMOTE 
                    display."
                ::= { xremote 4 }
            
            xremoteServerAccess2 OBJECT-TYPE
                SYNTAX Counter
                ACCESS read-only
                STATUS mandatory
                DESCRIPTION
                    "The number of times the system successfully 
                    accessed the XREMOTE secondary font server.  
                    Corresponds directly to the value labeled 'Attempts 
                    to access:', 'Server2', and 'Successful:' in the 
                    SERVER XREMOTE display."
                ::= { xremote 5 }
            
            xremoteServerAccessFailed2 OBJECT-TYPE
                SYNTAX Counter
                ACCESS read-only
                STATUS mandatory
                DESCRIPTION
                    "The number of times the system failed access to the 
                    XREMOTE secondary font server.  Corresponds directly 
                    to the value labeled 'Attempts to access:', 
                    'Server2', and 'Unsuccessful:' in the SERVER XREMOTE 
                    display."
                ::= { xremote 6 }
            
            xremoteSessions OBJECT-TYPE
                SYNTAX Gauge
                ACCESS read-only
                STATUS mandatory
                DESCRIPTION
                    "The number of connected XREMOTE sessions.  
                    Corresponds directly to the value labeled 'Current 
                    Number of Xremote Sessions:' in the SERVER XREMOTE 
                    display."
                ::= { xremote 7 }




            
            
                                                               [Page  75]


            
                                  XYPLEX INTERNET MIB        18 Oct 91
            
            
            
            -- the XREMOTE Port table
            
            xremotePortTable OBJECT-TYPE
                SYNTAX SEQUENCE OF XremotePortEntry
                ACCESS not-accessible
                STATUS mandatory
                DESCRIPTION
                    "A list of XREMOTE character port entries."
                ::= { xremote 8 }
            
            xremotePortEntry OBJECT-TYPE
                SYNTAX XremotePortEntry
                ACCESS not-accessible
                STATUS mandatory
                DESCRIPTION
                    "XREMOTE parameter values for a port."
                INDEX { psPortIndex }
                ::= { xremotePortTable 1 }
            
            XremotePortEntry ::=
                SEQUENCE {
                    xremotePortIndex
                        INTEGER,
                    xremotePortXremote
                        INTEGER
                }
            
            xremotePortIndex OBJECT-TYPE
                SYNTAX INTEGER
                ACCESS read-only
                STATUS mandatory
                DESCRIPTION
                    "An index value that uniquely identifies a port.  
                    The port identified by a particular value of this 
                    index is the same port as identified by 
                    charPortIndex in the Character MIB [11]."
                ::= { xremotePortEntry 1 }
            
            xremotePortXremote OBJECT-TYPE
                SYNTAX INTEGER { disabled(1), enabled(2) }
                ACCESS read-write
                STATUS mandatory
                DESCRIPTION
                    "Control for use of XREMOTE on the port.  
                    Corresponds directly to PORT XREMOTE and the 
                    presence of the label 'Xremote' following the label 

            
            
                                                               [Page  76]


            
                                  XYPLEX INTERNET MIB        18 Oct 91
            
            
            
                            'Enabled Characteristics:' in the PORT 
                    CHARACTERISTICS display."
                ::= { xremotePortEntry 2 }











































            
            
                                                               [Page  77]


            
                                  XYPLEX INTERNET MIB        18 Oct 91
            
            
            
            -- the Rotary group
            
            -- Implementation of this group is mandatory for all Xyplex
            -- systems that implement rotaries
            
            rotaryNumber OBJECT-TYPE
                SYNTAX INTEGER
                ACCESS read-only
                STATUS mandatory
                DESCRIPTION
                    "The number of entries in the Rotary  table."
                ::= { rotary 1 }


































            
            
                                                               [Page  78]


            
                                  XYPLEX INTERNET MIB        18 Oct 91
            
            
            
            -- The Rotary  table
            
            rotaryTable OBJECT-TYPE
                SYNTAX SEQUENCE OF RotaryEntry
                ACCESS not-accessible
                STATUS mandatory
                DESCRIPTION
                    "A list of rotary  entries."
                ::= { rotary 2 }
            
            rotaryEntry OBJECT-TYPE
                SYNTAX RotaryEntry
                ACCESS not-accessible
                STATUS mandatory
                DESCRIPTION
                    "Parameter values for a rotary."
                INDEX { rotaryAddress }
                ::= { rotaryTable 1 }
            
            RotaryEntry ::=
                SEQUENCE {
                    rotaryAddress
                        IpAddress,
                    rotaryStatus
                        INTEGER,
                    rotaryPortMap
                        OCTET STRING
                }
            
            rotaryAddress OBJECT-TYPE
                SYNTAX IpAddress
                ACCESS read-write
                STATUS mandatory
                DESCRIPTION
                    "The internet address to be recognized as a rotary.  
                    Corresponds directly to the ip-address portion of 
                    SERVER INTERNET ROTARY and the value labeled 
                    'Internet Address' in the SERVER INTERNET ROTARY 
                    display."
                ::= { rotaryEntry 1 }
            
            rotaryStatus OBJECT-TYPE
                SYNTAX INTEGER { invalid(1), valid(2) }
                ACCESS read-write
                STATUS mandatory
                DESCRIPTION

            
            
                                                               [Page  79]


            
                                  XYPLEX INTERNET MIB        18 Oct 91
            
            
            
                    "Status of this entry.  Setting the value to 
                    'invalid' invalidates the entry, corresponding 
                    directly to the CLEAR SERVER INTERNET ROTARY 
                    command.  It is an implementation-specific matter as 
                    to whether the agent removes an invalidated entry 
                    from the table."
                DEFVAL { valid }
                ::= { rotaryEntry 2 }
            
            rotaryPortMap OBJECT-TYPE
                SYNTAX OCTET STRING
                ACCESS read-write
                STATUS mandatory
                DESCRIPTION
                    "The list of character ports that compose the 
                    rotary.  The OCTET STRING contains a bitmap, with 
                    one bit for each port, and enough octets for all the 
                    ports on the system.  Port numbers are as defined 
                    for charPortIndex in the Character MIB [11].  
                    Corresponding bit numbers start with 1 as the 
                    high-order bit of the first octet.  Corresponds 
                    directly to port-list portion of SERVER INTERNET 
                    ROTARY and the value labeled 'Ports' in the SERVER 
                    INTERNET ROTARY display."
                ::= { rotaryEntry 3 }
            
            END



















            
            
                                                               [Page  80]


            
                                  XYPLEX INTERNET MIB        18 Oct 91
            
            
            
            7.  References
            
            [1]  V. Cerf, IAB Recommendations for the Development of 
            Internet Network Management Standards.  Internet Working 
            Group Request for Comments 1052.  Network Information 
            Center, SRI International, Menlo Park, California, (April, 
            1988).
            
            [2]  V. Cerf, Report of the Second Ad Hoc Network Management 
            Review Group, Internet Working Group Request for Comments 
            1109.  Network Information Center, SRI International, Menlo 
            Park, California, (August, 1989).
            
            [3]  M.T. Rose (editor), Management Information Base for 
            Network Management of TCP/IP-based internets, Internet 
            Working Group Request for Comments 1158.  Network 
            Information Center, SRI International, Menlo Park, 
            California, (May, 1990).
            
            [4]  M.T. Rose and K. McCloghrie, Structure and 
            Identification of Management Information for TCP/IP-based 
            internets, Internet Working Group Request for Comments 1155. 
            Network Information Center, SRI International, Menlo Park, 
            California, (May, 1990).
            
            [5]  K. McCloghrie and M.T. Rose, Management Information 
            Base for Network Management of TCP/IP-based 
            internets:MIB-II, Internet Working Group Request for 
            Comments 1213. Network Information Center, SRI 
            International, Menlo Park, California, (March 1991).
            
            [6]  J.D. Case, M.S. Fedor, M.L. Schoffstall, and J.R. 
            Davin, Simple Network Management Protocol, Internet Working 
            Group Request for Comments 1157.  Network Information 
            Center, SRI International, Menlo Park, California, (May, 
            1990).
            
            [7]  Information processing systems - Open Systems 
            Interconnection - Specification of Abstract Syntax Notation 
            One (ASN.1), International Organization for Standardization.  
            International Standard 8824, (December, 1987).
            
            [8]  Information processing systems - Open Systems 
            Interconnection - Specification of Basic Encoding Rules for 
            Abstract Notation One (ASN.1), International Organization 
            for Standardization.  International Standard 8825, 

            
            
                                                               [Page  81]


            
                                  XYPLEX INTERNET MIB        18 Oct 91
            
            
            
            (December, 1987).
            
            [9] M.T. Rose, K. McCloghrie (editors), Towards Concise MIB 
            Definitions, Internet Working Group Request for Comments 
            1212. Network Information Center, SRI International, Menlo 
            Park, California, (March, 1991).
            
            [10] Definitions of Managed Objects for Xyplex Systems, 
            Xyplex document number 420-0545, (August, 1991).
            
            [11] B. Stewart (editor), Definitions of Managed Objects for 
            Character Stream Devices, Internet Draft, (19 March 1991).
            

































            
            
                                                               [Page  82]

--
--
-- Copyright (C) 1996-2006 by SNMP Research, Incorporated.
--
-- This software is furnished under a license and may be used and copied
-- only in accordance with the terms of such license and with the
-- inclusion of the above copyright notice. This software or any other
-- copies thereof may not be provided or otherwise made available to any
-- other person. No title to and ownership of the software is hereby
-- transferred.
--
-- The information in this software is subject to change without notice
-- and should not be construed as a commitment by SNMP Research, Incorporated.
--
-- Restricted Rights Legend:
--  Use, duplication, or disclosure by the Government is subject to
--  restrictions as set forth in subparagraph (c)(1)(ii) of the Rights
--  in Technical Data and Computer Software clause at DFARS 252.227-7013;
--  subparagraphs (c)(4) and (d) of the Commercial Computer
--  Software-Restricted Rights Clause, FAR 52.227-19; and in similar
--  clauses in the NASA FAR Supplement and other corresponding
--  governmental regulations.
--
--

--
--                PROPRIETARY NOTICE
--
-- This software is an unpublished work subject to a confidentiality agreement
-- and is protected by copyright and trade secret law.  Unauthorized copying,
-- redistribution or other use of this work is prohibited.
--
-- The above notice of copyright on this source code product does not indicate
-- any actual or intended publication of such source code.
--
--
-- SNMP Research, Inc. grants permission to load this MIB onto your SNMP
-- management stations for use in configuring and managing LT-301 devices
-- and LATIN agents from SNMP Research.  SNMP Research, Inc. does not grant
-- permission to make additional copies, or distribute these MIBs to others
-- without written permission from SNMP Research, Inc.
--
--

SOFTTRAP-MIB DEFINITIONS ::= BEGIN

IMPORTS
    MODULE-IDENTITY, OBJECT-TYPE, NOTIFICATION-TYPE,
    ObjectName, Integer32, Counter32	                FROM SNMPv2-SMI
    StorageType, DisplayString,RowStatus, TimeStamp	FROM SNMPv2-TC
    SROwnerString                                       FROM SR-TC;


softTrap MODULE-IDENTITY
    LAST-UPDATED "9706191730"
    ORGANIZATION "SNMP Research, Inc."
    CONTACT-INFO "        David L. Battle
                          David B. Levi
                          David Reid
                          David Spakes

                  Postal: SNMP Research, Inc.
                          3001 Kimberlin Heights Road
                          Knoxville, TN  37920
                          US

                     Tel: +1 865 573 1434

                  E-mail: battle@snmp.com
                          levi@snmp.com
                          reid@snmp.com
                          spakes@snmp.com"
    DESCRIPTION
            "A MIB module for managing dynamically configured traps."
::= { snmpResearchMIBs 28}

snmpResearch                OBJECT IDENTIFIER ::= { enterprises 99 }
snmpResearchMIBs            OBJECT IDENTIFIER ::= { snmpResearch 12 }


softTrapMibTable OBJECT IDENTIFIER ::= { softTrap 1 }

softTrapTable OBJECT-TYPE
    SYNTAX     SEQUENCE OF SoftTrapEntry
    MAX-ACCESS not-accessible
    STATUS     current
    DESCRIPTION "A table describing dynamically configured traps."
::= { softTrapMibTable 1 }

softTrapEntry OBJECT-TYPE
    SYNTAX     SoftTrapEntry
    MAX-ACCESS not-accessible
    STATUS     current
    DESCRIPTION "An entry in the trap table."
    INDEX { softTrapIndex }
::= { softTrapTable 1 }

SoftTrapEntry ::= SEQUENCE {
    softTrapIndex         Integer32,
    softTrapName          DisplayString,
    softTrapGenTrap       INTEGER,
    softTrapSpecTrap      Integer32,
    softTrapEnterprise    OBJECT IDENTIFIER,
    softTrapV2TrapOID     OBJECT IDENTIFIER,
    softTrapOwner         SROwnerString,
    softTrapStorageType   StorageType,
    softTrapRowStatus     RowStatus
}

softTrapIndex OBJECT-TYPE
    SYNTAX     Integer32
    MAX-ACCESS not-accessible
    STATUS     current
    DESCRIPTION "A index for an entry in the softTrap table."
::= { softTrapEntry 1 }

softTrapName OBJECT-TYPE
    SYNTAX     DisplayString
    MAX-ACCESS read-create
    STATUS     current
    DESCRIPTION "A user-friendly name for the trap.  Presumably mibs
                 which refer to this table and are typically configured
                 by hand will refer to rows in this table by name rather
                 than by index.  The softTrapName should be unique for each
                 value of softTrapIndex."
::= { softTrapEntry 2 }

softTrapGenTrap OBJECT-TYPE
    SYNTAX     INTEGER {
                           coldStartTrap(0),
                           warmStartTrap(1),
                           linkDownTrap(2),
                           linkUpTrap(3),
                           authenFailureTrap(4),
                           egpNeighborLoss(5),
                           enterpriseTrap(6)
                       }
    MAX-ACCESS read-create
    STATUS     current
    DESCRIPTION "The softTrapGenTrap column contains the generic trap type."
::= { softTrapEntry 3 }

softTrapSpecTrap OBJECT-TYPE
    SYNTAX      Integer32
    MAX-ACCESS read-create
    STATUS     current
    DESCRIPTION "The value of this variable is only consulted when the
                 value of softTrapGenTrap is enterpriseTrap(6).

                 The softTrapSpecTrap column contains the enterprise-specific
                 trap type.  When setting up an SNMPv1 enterprise-specific
                 trap the value of this variable the value after the ::=
                 in the TRAP-TYPE macro.

                 When setting up an SNMPv2 enterprise-specific trap
                 this object should have value equal to the last sub-
                 identifier of the trap OID defined in the NOTIFICATION-TYPE
                 macro.

                 It is suggested that a value of 0 be used in this column
                 when softTrapGenTrap has any value other than
                 enterpriseTrap(6)."
    DEFVAL { 0 }
::= { softTrapEntry 4 }

softTrapEnterprise OBJECT-TYPE
    SYNTAX     OBJECT IDENTIFIER
    MAX-ACCESS read-create
    STATUS     current
    DESCRIPTION "The softTrapEnterprise column is used as the value for the
                 enterprise field in an SNMPv1 trap.  The value comes from
                 the ENTERPRISE clause in a TRAP_TYPE macro of a V1 MIB.  If
                 the SNMPv1 trap being set up is defined in a V2 MIB (in a
                 NOTIFICATION-TYPE macro), this variable's value should be
                 equal to the OBJECT IDENTIFIER of the trap without the last
                 sub-identifier."
::= { softTrapEntry 5 }

softTrapV2TrapOID OBJECT-TYPE
    SYNTAX     OBJECT IDENTIFIER
    MAX-ACCESS read-create
    STATUS     current
    DESCRIPTION "The softTrapV2Enterprise column is only used when setting up
                 an SNMPv2 enterprise specific trap.  The value of this
                 variable will be used as the value for the snmpTrapOID.0
                 VarBind in the SNMPv2 trap, and it is equal to the OID of the
                 trap as defined in the NOTIFICATION-TYPE macro of a V2 MIB.
                 If the SNMPv2 trap being sent is defined in a V1 MIB (in a
                 TRAP-TYPE macro), this column should be constructed from the
                 ENTERPRISE and the SNMPv1 specific trap number.  The
                 constructed value will be an OBJECT IDENTIFIER which is the
                 concatenation of the ENTERPRISE, 0, and the SNMPv1 specific
                 trap number."
::= { softTrapEntry 6 }

softTrapOwner OBJECT-TYPE
    SYNTAX     SROwnerString
    MAX-ACCESS read-create
    STATUS     current
    DESCRIPTION "The name of the management station who owns this row in
                 the softTrap table."
::= { softTrapEntry 7 }

softTrapStorageType OBJECT-TYPE
    SYNTAX     StorageType
    MAX-ACCESS read-create
    STATUS     current
    DESCRIPTION "A storage-type tag for this row.  See the description of the
                 StorageType textual-convention in the SNMPv2-TC document.
                 As of this writing this is RFC 1903."
::= { softTrapEntry 8 }

softTrapRowStatus OBJECT-TYPE
    SYNTAX     RowStatus
    MAX-ACCESS read-create
    STATUS     current
    DESCRIPTION "A row status for this row.  See the SNMPv2-TC document."
::= { softTrapEntry 9 }




softTrapVarBindListTable OBJECT-TYPE
    SYNTAX     SEQUENCE OF SoftTrapVarBindListEntry
    MAX-ACCESS not-accessible
    STATUS     current
    DESCRIPTION "A table containing the varbinds to be included in a softTrap."
::= { softTrapMibTable 2 }

softTrapVarBindListEntry OBJECT-TYPE
    SYNTAX     SoftTrapVarBindListEntry
    MAX-ACCESS not-accessible
    STATUS     current
    DESCRIPTION "An entry in the softTrapVarBindList table."
    INDEX { softTrapIndex, softTrapVarBindListSubIndex }
::= { softTrapVarBindListTable 1 }

SoftTrapVarBindListEntry ::= SEQUENCE {
    softTrapVarBindListSubIndex         Integer32,
    softTrapVarBindListObject           OBJECT IDENTIFIER,
    softTrapVarBindListInstanceSelector Integer32,
    softTrapVarBindListRowStatus        RowStatus
}

softTrapVarBindListSubIndex OBJECT-TYPE
    SYNTAX     Integer32
    MAX-ACCESS not-accessible
    STATUS     current
    DESCRIPTION "Since each row in the softTrap table may need more than
                 one VarBind, this sub index is included to index the
                 VarBinds which correspond to a single row in the softTrap
                 table."
::= { softTrapVarBindListEntry 1 }

softTrapVarBindListObject OBJECT-TYPE
    SYNTAX           OBJECT IDENTIFIER
    MAX-ACCESS read-create
    STATUS     current
    DESCRIPTION " "
::= { softTrapVarBindListEntry 2 }

softTrapVarBindListInstanceSelector OBJECT-TYPE
    SYNTAX Integer32
    MAX-ACCESS read-create
    STATUS     current
    DESCRIPTION "Some applications which use the softTrap table may wish
                 to provide one or more instance OBJECT IDENTIFIER fragments
                 to be appended to an OBJECT IDENTIFIER in a
                 softTrapVarBindListObject variable.  This object selects
                 which of those OBJECT IDENTIFIER fragments will be appended
                 to the softTrapVarBindListObject for this VarBind.  If
                 The OBJECT IDENTIFIER in this VarBind is a fully qualified
                 instance, then the value of this variable should be 0 to
                 indicate no instance fragment should be appended.  If the
                 value of this variable is 1 or greater it selects an
                 instance fragment to be appended from the application-
                 specific list which is made available when the trap
                 row cooresponding to this VarBind is activated.  If
                 this value select an instance fragment which does not
                 exist it is suggested that the implementation silently
                 omit this VarBind from the trap."
::= { softTrapVarBindListEntry 3 }

softTrapVarBindListRowStatus OBJECT-TYPE
    SYNTAX        RowStatus
    MAX-ACCESS read-create
    STATUS     current
    DESCRIPTION "A row status for the softTrapVarBindList table."
::= { softTrapVarBindListEntry 4 }


softTrapMibScalar OBJECT IDENTIFIER ::= { softTrap 2 }

softTrapNextIndex OBJECT-TYPE
    SYNTAX     Integer32
    MAX-ACCESS read-only
    STATUS     current
    DESCRIPTION "The index of a row in the softTrap table (a value of
                 softTrapIndex) which does not currently exist.  Presumably
                 this value will be used by manager stations to get
                 suggested index values to be used in subsequent set pdus when
                 creating a rows in the softTrap table.

                 Folklore:  Although it is technically left up to the
                 implementer to decide *which* non-existant index to
                 return, it is suggested that the implementer begin
                 by returning the smallest such index (excluding 0)
                 and continue to return the same index so long as
                 1) no row with that index is created and 2) this object
                 is accessed only by get-next (or get-bulk) pdus .  It is
                 further suggested that the agent implementation refrain from
                 returning the same index twice in response to different get
                 ``exact'' pdus but that it instead return progressively
                 larger (non-existent) indices as ``exact'' get requests come
                 in.  It is suggested that manager applications accessing this
                 object use get-next (or get-bulk) requests if they merely want
                 to scan the value of this object but do not intend to create
                 a row in the softTrap table.  If a manager station intends
                 to create a row in the softTrap table it is suggested
                 that they retrieve the value of this object using an
                 ``exact'' get pdu (not get-next or get-bulk).

                 None of the behavior described in the ``Folklore'' paragraph
                 above should be construed as a requirement, however following
                 the suggestions should result in few row-creation collisions."
                 
                
::= { softTrapMibScalar 1 }

END

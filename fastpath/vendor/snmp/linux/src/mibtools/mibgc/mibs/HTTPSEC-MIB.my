--
--
-- Copyright (C) 1996-2006 by SNMP Research, Incorporated.
--
-- This software is furnished under a license and may be used and copied
-- only in accordance with the terms of such license and with the
-- inclusion of the above copyright notice. This software or any other
-- copies thereof may not be provided or otherwise made available to any
-- other person. No title to and ownership of the software is hereby
-- transferred.
--
-- The information in this software is subject to change without notice
-- and should not be construed as a commitment by SNMP Research, Incorporated.
--
-- Restricted Rights Legend:
--  Use, duplication, or disclosure by the Government is subject to
--  restrictions as set forth in subparagraph (c)(1)(ii) of the Rights
--  in Technical Data and Computer Software clause at DFARS 252.227-7013;
--  subparagraphs (c)(4) and (d) of the Commercial Computer
--  Software-Restricted Rights Clause, FAR 52.227-19; and in similar
--  clauses in the NASA FAR Supplement and other corresponding
--  governmental regulations.
--
--

--
--                PROPRIETARY NOTICE
--
-- This software is an unpublished work subject to a confidentiality agreement
-- and is protected by copyright and trade secret law.  Unauthorized copying,
-- redistribution or other use of this work is prohibited.
--
-- The above notice of copyright on this source code product does not indicate
-- any actual or intended publication of such source code.
--
-- NOTICE:  This specification is Confidential information from
-- SNMP Research, Inc. unless/until it is published as an Internet Draft
-- or RFC.  Furthermore, the specification may change without notice.

HTTPSEC-MIB DEFINITIONS ::= BEGIN

IMPORTS
    OBJECT-IDENTITY, snmpDomains, MODULE-IDENTITY, OBJECT-TYPE,
    Integer32, Counter32
        FROM SNMPv2-SMI
    KeyChange
        FROM USEC-MIB
    RowStatus, TestAndIncr, StorageType, RowPointer
        FROM SNMPv2-TC
    HttpTCPIPAddress
        FROM SR-TC
    TransportLabel, AuthName
        FROM V2ADMIN-MIB
    MODULE-COMPLIANCE, OBJECT-GROUP
        FROM SNMPv2-CONF
    srExperimentalMIBs, srExperimentalDomains
        FROM SNMP-RESEARCH-MIB;
-- MIB in the right place these will "go away" when we put this

httpSecurityMIB MODULE-IDENTITY
    LAST-UPDATED "9610021700"
    ORGANIZATION "SNMP Research International"
    CONTACT-INFO "
		  Postal Address:

                  SNMP Research, Inc
                  3001 Kimberlin Heights Rd.
                  Knoxville, TN 37920-9716
                  USA

                  Tel:     +1 865 573 1434
                  Fax:     +1 865 573 9197
                  E-mail:  info@snmp.com
                  WWW:     http://www.snmp.com"
    DESCRIPTION
          "The MIB module for configuring the HTTP user-based
          authentication and privacy services.

          This MIB specification draws very heavily upon the
          SNMPv2* Administrative MIB."
    ::= { srExperimentalMIBs 1 }

-- HTTP over TCP over IP
-- DLP:  Are we allowed to simply designate this, or does it need to
-- be in "our" space?

httpTCPIPDomain  OBJECT-IDENTITY
    STATUS     current
    DESCRIPTION
            "The HTTP over TCP/IP transport domain.  The corresponding
            transport address is of type httpTCPIPAddress.  This
            definition is required in order to have an appropriate
            domain in the transportTable."
    ::= { srExperimentalDomains 1 }


SslVersion ::= TEXTUAL-CONVENTION
    DISPLAY-HINT "1d.1d"
    STATUS       current
    DESCRIPTION
            "Represents a SSL protocol version. The first octet gives
            the major version, and the second octet the minor version."
    REFERENCE
            "The SSL Protocol Version 3.0 [1], Appendix A."
    SYNTAX       OCTET STRING (SIZE (2))

SslCipherSuite ::= TEXTUAL-CONVENTION
    STATUS       current
    DESCRIPTION
            "Represents a SSL cipher suite."
    REFERENCE
            "The SSL Protocol Version 3.0 [1], Appendix C and E."
    SYNTAX       INTEGER {
                   -- Cipher Suite not listed here
                   noneOfTheBelow(1),
                   -- SSL V 3 Cipher Suites
                   sslNullWithNullNull(2),
                   sslRsaWithNullMd5(3),
                   sslRsaWithNullSha(4),
                   sslRsaExportWithRc440Md5(5),
                   sslRsaWithRc4128Md5(6),
                   sslRsaWithRc4128Sha(7),
                   sslRsaExportWithRc2Cbc40Md5(8),
                   sslRsaWithIdeaCbcSha(9),
                   sslRsaExportWithDes40CbcSha(10),
                   sslRsaWithDesCbcSha(11),
                   sslRsaWith3DesEdeCbcSha(12),
                   sslDhDssExportWithDes40CbcSha(13),
                   sslDhDssWithDesCbcSha(14),
                   sslDhDssWith3DesEdeCbcSha(15),
                   sslDhRsaExportWithDES40CbcSha(16),
                   sslDhRsaWithDesCbcSha(17),
                   sslDhRsaWith3DesEdeCbcSha(18),
                   sslDheDssExportWithDes40CbcSha(19),
                   sslDheDssWithDesCbcSha(20),
                   sslDheDssWith3DesEdeCbcSha(21),
                   sslDheRsaExportWithDes40CbcSha(22),
                   sslDheRsaWithDesCbcSha(23),
                   sslDheRsaWith3DesEdeCbcSha(24),
                   sslDhAnonExportWithRc440Md5(25),
                   sslDhAnonWithRc4128Md5(26),
                   sslDhAnonExportWithDes40CbcSha(27),
                   sslDhAnonWithDesCbcSha(28),
                   sslDhAnonWith3DesEdeCbcSha(29),
                   sslFortezzaDmsWithNullSha(30),
                   sslFortezzaDmsWithFortezzaCbcSha(31),
                   -- SSL V 2 Cipher Suites
                   sslV2Rc4128WithMd5(32),
                   sslV2Rc4128Export40WithMd5(33),
                   sslV2Rc2Cbc128CbcWithMd5(34),
                   sslV2Rc2Cbc128CbcExport40WithMd5(35),
                   sslV2Idea128CbcWithMd5(36),
                   sslV2Des64CbcWithMd5(37),
                   sslV2Des192Ede3CcdWithMd5(38)
                 }

SslCertificate ::= TEXTUAL-CONVENTION
    STATUS       current
    DESCRIPTION
            "Represents a SSL certificate.  Note that in practice this
             size limitation is sufficient.  In theory, however, a
             certificate may indeed be much larger than 64k."
    REFERENCE
            "The SSL Protocol Version 3.0 [1], Section 7.6.2."
    SYNTAX       OCTET STRING (SIZE (0..65535))

--
-- The httpSecStats group.  This group contains objects which provide
-- statistics for the HTTP user-based security and privacy services.
--

httpSecStats OBJECT IDENTIFIER ::= { httpSecurityMIB 1 }

httpStatsNoAuthentications OBJECT-TYPE
    SYNTAX       Counter32
    MAX-ACCESS   read-only
    STATUS       current
    DESCRIPTION
          "A count of the number of received HTTP requests that did
          not contain any authentication information."
    ::= { httpSecStats 1 }

httpStatsUnknownUserNames OBJECT-TYPE
    SYNTAX       Counter32
    MAX-ACCESS   read-only
    STATUS       current
    DESCRIPTION
          "A count of the number of received HTTP requests with
          usernames that were not found in the httpUserNameTable."
    ::= { httpSecStats 2 }

httpStatsWrongPasswords OBJECT-TYPE
    SYNTAX       Counter32
    MAX-ACCESS   read-only
    STATUS       current
    DESCRIPTION
          "A count of the number of received HTTP requests with
          passwords that did not match the ones in the
          httpUserNameTable."
    ::= { httpSecStats 3 }

--
-- The httpUser group
--

httpUser OBJECT IDENTIFIER ::= { httpSecurityMIB 2 }

httpUserSpinLock OBJECT-TYPE
    SYNTAX       TestAndIncr
    MAX-ACCESS   read-write
    STATUS       current
    DESCRIPTION
          "An advisory lock used to allow several cooperating SNMPv2*
          entities, all acting in a manager role, to coordinate their
          use of set operations to entries in the httpUserNameTable.
          A manager application should include the value of
          httpUserSpinLock in every set operation which accesses the
          httpUserNameTable.  Since this is an advisory lock, entities
          acting in an agent role do not enforce the use of
          httpUserSpinLock."
    ::= { httpUser 1 }

httpMaxUserNameLength OBJECT-TYPE
    SYNTAX       Integer32 (0..32)
    MAX-ACCESS   read-only
    STATUS       current
    DESCRIPTION
          "The maximum length of httpUserName allowed by this
          implementation.  This value can be probed by a management
          application prior to attempting a row creation operation in
          the httpUserNameTable.  A value of 0 indicates that the
          httpUserNameTable does not allow row creation or deletion
          operations."
    ::= { httpUser 2 }

-- The httpUserNameTable
--
-- The httpUserNameTable contains the database of users who are configured
-- to perform HTTP communications with HTTP-enabled SNMPv2* entities
-- via the HTTP User-based authentication and privacy service.
--
-- These users are organized into 'groups'.  The group to which a user
-- belongs is specified in the httpUserGroupName object.
--
-- Access privileges are assigned by group in the acTable as defined
-- in the SNMPv2* Administrative Framework document.
-- This allows groups of users to share the same privileges or for
-- individual users to have their own unique privileges.
--
-- In order to ease the task of configuring SNMPv2* entities, the
-- httpUserName used to index in the following table is a textual
-- (human-readable) string.
--
-- Experience has shown that it is sometimes necessary for a network
-- administrator to manually edit the configuration datastore for
-- an SNMPv2* entity, and the use of textual strings for indices makes
-- the configuration datastore much easier for administrators to
-- maintain.
--
-- An implementation may restrict the lengths of httpUserName and
-- httpUserGroupName entries to less than the maximum value.
--
-- The httpMaxUserNameLength variable defined above and the
-- maxGroupNameLength variable defined in the SNMPv2* Administrative
-- Framework document can be used to detect the maximum length of
-- name strings supported by a particular implementation.

httpUserNameTable OBJECT-TYPE
    SYNTAX       SEQUENCE OF HttpUserNameEntry
    MAX-ACCESS   not-accessible
    STATUS       current
    DESCRIPTION
          "The SNMPv2* database for httpAuth(12673) and
           httpSSLPriv(12674) users."
    ::= { httpUser 3 }

httpUserNameEntry OBJECT-TYPE
    SYNTAX       HttpUserNameEntry
    MAX-ACCESS   not-accessible
    STATUS       current
    DESCRIPTION
          "Information about a particular HTTP user."
    INDEX { IMPLIED httpUserName }
    ::= { httpUserNameTable 1 }

HttpUserNameEntry ::= SEQUENCE {
    httpUserName             AuthName,
    httpUserGroupName        AuthName,
    httpUserPasswordChange   KeyChange,
    httpUserNovel            OCTET STRING,
    httpUserTransportLabel   TransportLabel,
    httpUserCloneFrom        RowPointer,
    httpUserStorageType      StorageType,
    httpUserStatus           RowStatus
}

httpUserName OBJECT-TYPE
    SYNTAX       AuthName (SIZE(1..32))
    MAX-ACCESS   not-accessible
    STATUS       current
    DESCRIPTION
          "This variable contains the textual name of a user."
    ::= { httpUserNameEntry 1 }

httpUserGroupName OBJECT-TYPE
    SYNTAX       AuthName (SIZE(0..32))
    MAX-ACCESS   read-create
    STATUS       current
    DESCRIPTION
          "This variable contains the textual name of the group to
          which a user belongs.  A group name of zero length indicates
          that the user is not [perhaps yet] a member of any group,
          possibly because the entry has not yet been completely
          configured.  Users which are not a part of any group are
          effectively disabled from communicating with the HTTP-
          enabled SNMPv2* entity."
    DEFVAL { ''H }     -- the empty string
    ::= { httpUserNameEntry 2 }

httpUserPasswordChange OBJECT-TYPE
    SYNTAX       KeyChange
    MAX-ACCESS   read-create
    STATUS       current
    DESCRIPTION
          "An object, which when modified, causes the user's
          password to be modified via a one-way function.

          When creating a new user, it is an 'inconsistentName' error
          for a set operation to refer to this object unless it is
          previously or concurrently initialized through a set
          operation on the corresponding value of httpUserCloneFrom."
    DEFVAL { ''H }     -- the empty string
    ::= { httpUserNameEntry 3 }

httpUserNovel OBJECT-TYPE
    SYNTAX       OCTET STRING (SIZE(0..20))
    MAX-ACCESS   read-create
    STATUS       current
    DESCRIPTION
          "This object may be used by a manager as a part of its
          procedure for altering secret information about a user.
          By altering the value of an instance of this object in
          the same Set-Request used to update secret information,
          a subsequent Get-Request can determine if the Set-Request
          was successful in the event that no response to the
          Set-Request is received.

          When an instance of this object is created, its value is
          initialized to a random value.  Therefore, there is no DEFVAL
          clause.

          This object need not be stored in non-volatile storage and
          should be initialized to an unpredictable value upon system
          reinitialization."
    ::= { httpUserNameEntry 4 }

httpUserTransportLabel OBJECT-TYPE
    SYNTAX       TransportLabel
    MAX-ACCESS   read-create
    STATUS       current
    DESCRIPTION
          "This object specifies a set of transport endpoints from which
          an agent will accept management requests.  If a management
          request generated on behalf of this user is received on a
          transport endpoint other than the transport endpoints
          identified by this object, the request is deemed unauthentic.

          The transports identified by this object are specified in
          the transportTable.  Entries in the transportTable whose
          transportLabel value are equal to this object are identified.

          If the value of this object has zero-length, or if the
          transportTable is not implemented, transport endpoints
          are not checked when authenticating messages generated
          by this user."
     REFERENCE "transportTable is defined in The SNMPv2*
                Administrative Framework and MIB"
     DEFVAL { ''H }     -- the empty string
    ::= { httpUserNameEntry 5 }

httpUserCloneFrom OBJECT-TYPE
    SYNTAX       RowPointer (SIZE(12..266))
    MAX-ACCESS   read-create
    STATUS       current
    DESCRIPTION
          "An indication of the user from which to clone authentication
          and privacy parameters.  When read, the value { 0 0 } is
          returned.

          This object must be written exactly once, when the associated
          instance of httpUserStatus either does not exist or has the
          value `notReady'.  Subsequent set operations to this object
          will succeed, but will not cause the agent to take any action.
          When first written, the value identifies an instance of
          a user, the cloning user, whose status column has the value
          'active' or 'not in service'.

          The authentication password of the cloning user is copied to
          the corresponding authentication password of the user being
          created.

          For implementations which have a static, fixed number of rows
          in this table and for which row creation is not supported (the
          maximum value of userNameLength is zero) need not implement
          this object."

    ::= { httpUserNameEntry 6 }

httpUserStorageType OBJECT-TYPE
    SYNTAX       StorageType
    MAX-ACCESS   read-create
    STATUS       current
    DESCRIPTION
          "The storage type for this conceptual row in the
          httpUserNameTable.

          Conceptual rows having the value 'permanent' must allow
          write-access at a minimum to httpUserGroupName,
          httpUserPasswordChange, and httpUserNovel."
    ::= { httpUserNameEntry 7 }

httpUserStatus OBJECT-TYPE
    SYNTAX       RowStatus
    MAX-ACCESS   read-create
    STATUS       current
    DESCRIPTION
          "The status of this conceptual row in the httpUserNameTable.

          A user is not qualified for activation until instances of
          all implemented columns of its userNameEntry row have an
          appropriate value.  In particular, one or more management
          set operations are required to configure the entry.
          Until instances of all corresponding columns and secrets are
          appropriately configured, the value of the corresponding
          instance of the userStatus column is `notReady'."
    ::= { httpUserNameEntry 8 }

--
-- SSL configuration objects
--
-- Note that while these objects are intended to be used to control
-- the options that the SSL uses in communication with Web browsers,
-- it may not be the case that the particular SSL implementation
-- allows for such control.

sslConfig OBJECT IDENTIFIER ::= { httpSecurityMIB 3 }

sslVersion OBJECT-TYPE
    SYNTAX       SslVersion
    MAX-ACCESS   read-only
    STATUS       current
    DESCRIPTION
          "The version of the SSL protocol used by this agent."
    ::= { sslConfig 1 }

sslSupportedCipherSuites OBJECT-TYPE
    SYNTAX       BITS {
                   noneOfTheBelow(1),
                   sslNullWithNullNull(2),
                   sslRsaWithNullMd5(3),
                   sslRsaWithNullSha(4),
                   sslRsaExportWithRc440Md5(5),
                   sslRsaWithRc4128Md5(6),
                   sslRsaWithRc4128Sha(7),
                   sslRsaExportWithRc2Cbc40Md5(8),
                   sslRsaWithIdeaCbcSha(9),
                   sslRsaExportWithDes40CbcSha(10),
                   sslRsaWithDesCbcSha(11),
                   sslRsaWith3DesEdeCbcSha(12),
                   sslDhDssExportWithDes40CbcSha(13),
                   sslDhDssWithDesCbcSha(14),
                   sslDhDssWith3DesEdeCbcSha(15),
                   sslDhRsaExportWithDES40CbcSha(16),
                   sslDhRsaWithDesCbcSha(17),
                   sslDhRsaWith3DesEdeCbcSha(18),
                   sslDheDssExportWithDes40CbcSha(19),
                   sslDheDssWithDesCbcSha(20),
                   sslDheDssWith3DesEdeCbcSha(21),
                   sslDheRsaExportWithDes40CbcSha(22),
                   sslDheRsaWithDesCbcSha(23),
                   sslDheRsaWith3DesEdeCbcSha(24),
                   sslDhAnonExportWithRc440Md5(25),
                   sslDhAnonWithRc4128Md5(26),
                   sslDhAnonExportWithDes40CbcSha(27),
                   sslDhAnonWithDesCbcSha(28),
                   sslDhAnonWith3DesEdeCbcSha(29),
                   sslFortezzaDmsWithNullSha(30),
                   sslFortezzaDmsWithFortezzaCbcSha(31),
                   sslV2Rc4128WithMd5(32),
                   sslV2Rc4128Export40WithMd5(33),
                   sslV2Rc2Cbc128CbcWithMd5(34),
                   sslV2Rc2Cbc128CbcExport40WithMd5(35),
                   sslV2Idea128CbcWithMd5(36),
                   sslV2Des64CbcWithMd5(37),
                   sslV2Des192Ede3CcdWithMd5(38)
                 }
    MAX-ACCESS   read-only
    STATUS       current
    DESCRIPTION
          "The SSL cipher suites supported by this agent."
    ::= { sslConfig 2 }

sslCipherSuiteSpinLock OBJECT-TYPE
    SYNTAX       TestAndIncr
    MAX-ACCESS   read-write
    STATUS       current
    DESCRIPTION
          "An advisory lock used to allow several cooperating SNMPv2*
          entities, all acting in a manager role, to coordinate their
          use of set operations to entries in the sslCipherSuiteTable.
          A manager application should include the value of
          sslCipherSuiteSpinLock in every set operation which accesses
          the sslCipherSuiteTable.  Since this is an advisory lock,
          entities acting in an agent role do not enforce the use of
          sslCipherSuiteSpinLock."
    ::= { sslConfig 3 }

sslCipherSuiteTable OBJECT-TYPE
    SYNTAX       SEQUENCE OF SslCipherSuiteEntry
    MAX-ACCESS   not-accessible
    STATUS       current
    DESCRIPTION
          "Table allowing configuration of which SSL Cipher Suites
          are used and their priority."
    ::= { sslConfig 4 }

sslCipherSuiteEntry OBJECT-TYPE
    SYNTAX       SslCipherSuiteEntry
    MAX-ACCESS   not-accessible
    STATUS       current
    DESCRIPTION
          "One row of the "
    INDEX { sslCipherSuiteIndex }
    ::= { sslCipherSuiteTable 1 }

SslCipherSuiteEntry ::= SEQUENCE {
    sslCipherSuiteIndex         Integer32,
    sslCipherSuite              SslCipherSuite,
    sslCipherSuitePriority      Integer32,
    sslCipherSuiteStorageType   StorageType,
    sslCipherSuiteStatus        RowStatus
}

sslCipherSuiteIndex OBJECT-TYPE
    SYNTAX       Integer32 (0..255)
    MAX-ACCESS   not-accessible
    STATUS       current
    DESCRIPTION
          "A simple integer index"
    ::= { sslCipherSuiteEntry 1 }

sslCipherSuite OBJECT-TYPE
    SYNTAX       SslCipherSuite
    MAX-ACCESS   read-create
    STATUS       current
    DESCRIPTION
          "The name of the SSL Cipher Suite"
    ::= { sslCipherSuiteEntry 2 }

sslCipherSuitePriority OBJECT-TYPE
    SYNTAX       Integer32 (0..255)
    MAX-ACCESS   read-create
    STATUS       current
    DESCRIPTION
          "The priority assigned to this particular cipher suite.  The
          lower the value, the higher the priority (i.e., 0 is the
          highest and 255 the lowest).  During connection negotiation,
          the SSL peers negotiate, and, where possible the cipher
          suites should be chosen by the priority values in this
          object."
    ::= { sslCipherSuiteEntry 3 }

sslCipherSuiteStorageType OBJECT-TYPE
    SYNTAX       StorageType
    MAX-ACCESS   read-create
    STATUS       current
    DESCRIPTION
          "The storage type for this conceptual row in the
          sslCipherSuiteTable."
    ::= { sslCipherSuiteEntry 4 }

sslCipherSuiteStatus OBJECT-TYPE
    SYNTAX       RowStatus
    MAX-ACCESS   read-create
    STATUS       current
    DESCRIPTION
          "The status of this conceptual row in the sslCipherSuiteTable."
    ::= { sslCipherSuiteEntry 5 }

sslServerCertificate OBJECT-TYPE
    SYNTAX       SslCertificate
    MAX-ACCESS   read-write
    STATUS       current
    DESCRIPTION
          "The SSL server certificate for this agent. A zero length
          value means that the agent should not authenticate itself
          using a certificate."
    ::= { sslConfig 5 }

--
-- conformance information
--

httpSecMIBConformance
               OBJECT IDENTIFIER ::= { httpSecurityMIB 4 }
httpSecMIBCompliances
               OBJECT IDENTIFIER ::= { httpSecMIBConformance 1 }
httpSecMIBGroups
               OBJECT IDENTIFIER ::= { httpSecMIBConformance 2 }

--
-- compliance statements
--
--
-- It is *strongly* suggested that readers do not attempt to decipher
-- this section without consulting the narrative and tables
-- accompanying this MIB module.  See section 6, "Conformance" for
-- details.
--

httpSecMIBhttpAuthStaticCompliance MODULE-COMPLIANCE
    STATUS    current
    DESCRIPTION
          "The compliance statement for a HTTP-enabled SNMPv2* entity
          without SSL (only implements httpAuth) which implements the
          SNMPv2* HTTPSEC MIB with read-only access to the MIB objects."

    MODULE  -- this module
        MANDATORY-GROUPS {
                          httpSecMIBStatsGroup,
                          httpSecMIBUserNameInfoGroup,
                          httpSecMIBUserParametersGroup
                         }

        OBJECT           httpUserGroupName
        MIN-ACCESS       read-only
        DESCRIPTION
              "Read-write access and read-create access are
              not required."

        OBJECT           httpUserTransportLabel
        MIN-ACCESS       read-only
        DESCRIPTION
              "Read-write access and read-create access are
              not required."

        OBJECT           httpUserStorageType
        SYNTAX           INTEGER {
                          readOnly(5) -- e.g., completely in ROM
                         }
        MIN-ACCESS       read-only
        DESCRIPTION
              "Read-write access and read-create access are
              not required.

              Support of the values other(1), volatile(2),
              nonVolatile(3), and permanent(4) is not required."

    ::= { httpSecMIBCompliances 1 }

httpSecMIBhttpAuthPermanentCompliance MODULE-COMPLIANCE
    STATUS    current
    DESCRIPTION
          "The compliance statement for a HTTP-enabled SNMPv2* entity
          without SSL (only implements httpAuth) which implements the
          SNMPv2* HTTPSEC MIB with read-write access to the MIB objects."

    MODULE  -- this module
        MANDATORY-GROUPS {
                          httpSecMIBStatsGroup,
                          httpSecMIBUserNameInfoGroup,
                          httpSecMIBUserParametersGroup,
                          httpSecMIBPasswordUpdateGroup
                         }

        OBJECT           httpUserGroupName
        MIN-ACCESS       read-write
        DESCRIPTION
              "Read-create access is not required."

        OBJECT           httpUserPasswordChange
        MIN-ACCESS       read-write
        DESCRIPTION
              "Read-create access is not required."

        OBJECT           httpUserNovel
        MIN-ACCESS       read-write
        DESCRIPTION
              "Read-create access is not required."
        OBJECT           httpUserTransportLabel
        MIN-ACCESS       read-only
        DESCRIPTION
              "Read-write access and read-create access are
              not required."

        OBJECT           httpUserStorageType
        SYNTAX           INTEGER {
                          permanent(4) -- e.g., partially in ROM
                         }
        MIN-ACCESS       read-only
        DESCRIPTION
              "Read-write access and read-create access are
              not required.

              Support of the values other(1), volatile(2),
              nonVolatile(3), and readOnly(5) is not required."

    ::= { httpSecMIBCompliances 2 }

httpSecMIBhttpAuthFullCompliance MODULE-COMPLIANCE
    STATUS    current
    DESCRIPTION
          "The compliance statement for a HTTP-enabled SNMPv2* entity
          without SSL (only implements httpAuth) which implements the
          SNMPv2* HTTPSEC MIB with read-create access to the MIB objects."

    MODULE  -- this module
        MANDATORY-GROUPS {
                          httpSecMIBStatsGroup,
                          httpSecMIBUserNameInfoGroup,
                          httpSecMIBUserParametersGroup,
                          httpSecMIBPasswordUpdateGroup,
                          httpSecMIBUserCreationGroup
                         }

    ::= { httpSecMIBCompliances 3 }

httpSecMIBhttpSSLPrivStaticCompliance MODULE-COMPLIANCE
    STATUS    current
    DESCRIPTION
          "The compliance statement for a HTTP-enabled SNMPv2* entity
          with SSL (implements httpAuth and httpSSLPriv) which implements
          the SNMPv2* HTTPSEC MIB with read-only access to the MIB objects."

    MODULE  -- this module
        MANDATORY-GROUPS {
                          httpSecMIBStatsGroup,
                          httpSecMIBUserNameInfoGroup,
                          httpSecMIBUserParametersGroup,
                          httpSecMIBsslInfoGroup
                         }

        OBJECT           httpUserGroupName
        MIN-ACCESS       read-only
        DESCRIPTION
              "Read-write access and read-create access are
              not required."

        OBJECT           httpUserTransportLabel
        MIN-ACCESS       read-only
        DESCRIPTION
              "Read-write access and read-create access are
              not required."

        OBJECT           httpUserStorageType
        SYNTAX           INTEGER {
                          readOnly(5) -- e.g., completely in ROM
                         }
        MIN-ACCESS       read-only
        DESCRIPTION
              "Read-write access and read-create access are
              not required.

              Support of the values other(1), volatile(2),
              nonVolatile(3), and permanent(4) is not required."

        OBJECT           sslCipherSuite
        MIN-ACCESS       read-only
        DESCRIPTION
              "Read-write access and read-create access are
              not required."

        OBJECT           sslCipherSuitePriority
        MIN-ACCESS       read-only
        DESCRIPTION
              "Read-write access and read-create access are
              not required."

        OBJECT           sslCipherSuiteStorageType
        SYNTAX           INTEGER {
                          readOnly(5) -- e.g., completely in ROM
                         }
        MIN-ACCESS       read-only
        DESCRIPTION
              "Read-write access and read-create access are
              not required.

              Support of the values other(1), volatile(2),
              nonVolatile(3), and permanent(4) is not required."

        OBJECT           sslServerCertificate
        MIN-ACCESS       read-only
        DESCRIPTION
              "Read-write access is not required."

    ::= { httpSecMIBCompliances 4 }

httpSecMIBhttpSSLPrivPermanentCompliance MODULE-COMPLIANCE
    STATUS    current
    DESCRIPTION
          "The compliance statement for a HTTP-enabled SNMPv2* entity
          with SSL (implements httpAuth and httpSSLPriv) which implements
          the SNMPv2* HTTPSEC MIB with read-write access to the MIB objects."

    MODULE  -- this module
        MANDATORY-GROUPS {
                          httpSecMIBStatsGroup,
                          httpSecMIBUserNameInfoGroup,
                          httpSecMIBUserParametersGroup,
                          httpSecMIBPasswordUpdateGroup,
                          httpSecMIBsslInfoGroup
                         }

        OBJECT           httpUserGroupName
        MIN-ACCESS       read-write
        DESCRIPTION
              "Read-create access is not required."

        OBJECT           httpUserPasswordChange
        MIN-ACCESS       read-write
        DESCRIPTION
              "Read-create access is not required."

        OBJECT           httpUserNovel
        MIN-ACCESS       read-write
        DESCRIPTION
              "Read-create access is not required."

        OBJECT           httpUserTransportLabel
        MIN-ACCESS       read-only
        DESCRIPTION
              "Read-write access and read-create access are
              not required."

        OBJECT           httpUserStorageType
        SYNTAX           INTEGER {
                          permanent(4) -- e.g., partially in ROM
                         }
        MIN-ACCESS       read-only
        DESCRIPTION
              "Read-write access and read-create access are
              not required.

              Support of the values other(1), volatile(2),
              nonVolatile(3), and readOnly(5) is not required."

        OBJECT           sslCipherSuite
        MIN-ACCESS       read-only
        DESCRIPTION
              "Read-write access and read-create access are
              not required."

        OBJECT           sslCipherSuitePriority
        MIN-ACCESS       read-only
        DESCRIPTION
              "Read-write access and read-create access are
              not required."

        OBJECT           sslCipherSuiteStorageType
        SYNTAX           INTEGER {
                          readOnly(5) -- e.g., completely in ROM
                         }
        MIN-ACCESS       read-only
        DESCRIPTION
              "Read-write access and read-create access are
              not required.

              Support of the values other(1), volatile(2),
              nonVolatile(3), and permanent(4) is not required."
        OBJECT           sslServerCertificate
        MIN-ACCESS       read-only
        DESCRIPTION
              "Read-write access is not required."

    ::= { httpSecMIBCompliances 5 }

httpSecMIBhttpSSLPrivFullCompliance MODULE-COMPLIANCE
    STATUS    current
    DESCRIPTION
          "The compliance statement for a HTTP-enabled SNMPv2* entity
          with SSL (implements httpAuth and httpSSLPriv) which implements
          the SNMPv2* HTTPSEC MIB with read-create access to the MIB objects."

    MODULE  -- this module
        MANDATORY-GROUPS {
                          httpSecMIBStatsGroup,
                          httpSecMIBUserNameInfoGroup,
                          httpSecMIBUserParametersGroup,
                          httpSecMIBPasswordUpdateGroup,
                          httpSecMIBUserCreationGroup,
                          httpSecMIBsslInfoGroup,
                          httpSecMIBsslConfigGroup
                         }

    ::= { httpSecMIBCompliances 6 }

-- units of conformance

httpSecMIBStatsGroup OBJECT-GROUP
    OBJECTS {
             httpStatsNoAuthentications,
             httpStatsUnknownUserNames,
             httpStatsWrongPasswords
            }
    STATUS    current
    DESCRIPTION
            "Objects counting the possible authentication errors."
    ::= { httpSecMIBGroups 1 }

httpSecMIBUserNameInfoGroup OBJECT-GROUP
    OBJECTS {
             httpMaxUserNameLength
            }
    STATUS    current
    DESCRIPTION
            "Information about user names on the managed system."
    ::= { httpSecMIBGroups 2 }

httpSecMIBUserParametersGroup OBJECT-GROUP
    OBJECTS {
             httpUserGroupName,
             httpUserTransportLabel,
             httpUserStorageType
            }
    STATUS    current
    DESCRIPTION
            "Information pertaining to a particular user."
    ::= { httpSecMIBGroups 3 }

httpSecMIBPasswordUpdateGroup OBJECT-GROUP
    OBJECTS {
             httpUserSpinLock,
             httpUserPasswordChange,
             httpUserNovel
            }
    STATUS    current
    DESCRIPTION
            "The objects required to support remote management
            of passwords via this MIB module."
    ::= { httpSecMIBGroups 4 }

httpSecMIBUserCreationGroup OBJECT-GROUP
    OBJECTS {
             httpUserCloneFrom,
             httpUserStatus
            }
    STATUS    current
    DESCRIPTION
            "The objects required to support user creation
            via this MIB module."
    ::= { httpSecMIBGroups 5 }

httpSecMIBSslInfoGroup OBJECT-GROUP
    OBJECTS {
             sslVersion,
             sslSupportedCipherSuites,
             sslCipherSuite,
             sslCipherSuitePriority,
             sslCipherSuiteStorageType,
             sslServerCertificate
            }
    STATUS    current
    DESCRIPTION
            "Objects giving basic information and configurability of the
            Secure Socket Layer."
    ::= { httpSecMIBGroups 6 }

httpSecMIBSslConfigGroup OBJECT-GROUP
    OBJECTS {
             sslCipherSuiteSpinLock,
             sslCipherSuiteStatus
            }
    STATUS    current
    DESCRIPTION
            "Objects for configuring new SSL cipher suites."
    ::= { httpSecMIBGroups 7 }

END

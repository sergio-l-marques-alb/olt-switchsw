--
--
-- Copyright (C) 1996-2006 by SNMP Research, Incorporated.
--
-- This software is furnished under a license and may be used and copied
-- only in accordance with the terms of such license and with the
-- inclusion of the above copyright notice. This software or any other
-- copies thereof may not be provided or otherwise made available to any
-- other person. No title to and ownership of the software is hereby
-- transferred.
--
-- The information in this software is subject to change without notice
-- and should not be construed as a commitment by SNMP Research, Incorporated.
--
-- Restricted Rights Legend:
--  Use, duplication, or disclosure by the Government is subject to
--  restrictions as set forth in subparagraph (c)(1)(ii) of the Rights
--  in Technical Data and Computer Software clause at DFARS 252.227-7013;
--  subparagraphs (c)(4) and (d) of the Commercial Computer
--  Software-Restricted Rights Clause, FAR 52.227-19; and in similar
--  clauses in the NASA FAR Supplement and other corresponding
--  governmental regulations.
--
--

--
--                PROPRIETARY NOTICE
--
-- This software is an unpublished work subject to a confidentiality agreement
-- and is protected by copyright and trade secret law.  Unauthorized copying,
-- redistribution or other use of this work is prohibited.
--
-- The above notice of copyright on this source code product does not indicate
-- any actual or intended publication of such source code.
--

   SNMP-RESEARCH-AUTODISCOVERY-MIB DEFINITIONS ::= BEGIN

   IMPORTS
       MODULE-IDENTITY, NOTIFICATION-TYPE, enterprises
           FROM SNMPv2-SMI

       MODULE-COMPLIANCE, NOTIFICATION-GROUP
           FROM SNMPv2-CONF;

   srAutoDiscovery MODULE-IDENTITY
       LAST-UPDATED "200101121015Z"
       ORGANIZATION "SNMP Research, Incorporated"
       CONTACT-INFO "SNMP Research, Incorporated
                     3001 Kimberlin Heights Road
                     Knoxville, TN 37920-9716
                     U.S.A.
                     Voice:   +1 865 573 1434
                     E-mail:  support@snmp.com"
       DESCRIPTION
           "This MIB module defines a set of SNMP Research proprietary
            objects for the autodiscovery of IP network information."
       ::= { enterprises 99 12 44 }


   --
   --   Groups defined in this MIB module.
   --
   srADObjects       OBJECT IDENTIFIER ::= { srAutoDiscovery 1 }
   srADNotifications OBJECT IDENTIFIER ::= { srAutoDiscovery 2 }
   srADConformance   OBJECT IDENTIFIER ::= { srAutoDiscovery 3 }


   --
   --   Notifications.
   --
   srADTraps OBJECT IDENTIFIER ::= { srADNotifications 0 }

   srADManagerProbeTrap NOTIFICATION-TYPE
       STATUS      current
       DESCRIPTION
           "This notification is generated by the autodiscovery
            engine to probe for SNMP managers which are listening on
            the default notification port (usually UDP port 162)."
       ::= { srADTraps 1 }


   --
   --   Conformance information.
   --
   srADCompliances OBJECT IDENTIFIER ::= { srADConformance 1 }
   srADGroups      OBJECT IDENTIFIER ::= { srADConformance 2 }


   --
   --   Compliance statements.
   --
   srADCompliance MODULE-COMPLIANCE
      STATUS  current
      DESCRIPTION
              "The compliance statement for the 
                SNMP-RESEARCH-AUTODISCOVERY-MIB."
      MODULE  -- this module
      MANDATORY-GROUPS {
            srADNotificationsGroup
      }
      ::= { srADCompliances 1 }


   --
   --   MIB object groupings.
   --
   srADNotificationsGroup NOTIFICATION-GROUP
       NOTIFICATIONS {
           srADManagerProbeTrap
       }
       STATUS      current
       DESCRIPTION
           "The notifications emitted by the autodiscovery engine."
       ::= { srADGroups 1 }

   END

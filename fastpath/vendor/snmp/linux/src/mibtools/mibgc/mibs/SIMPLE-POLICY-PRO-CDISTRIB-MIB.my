--
--
-- Copyright (C) 1999-2006 by SNMP Research, Incorporated.
--
-- This software is furnished under a license and may be used and copied
-- only in accordance with the terms of such license and with the
-- inclusion of the above copyright notice. This software or any other
-- copies thereof may not be provided or otherwise made available to any
-- other person. No title to and ownership of the software is hereby
-- transferred.
--
-- The information in this software is subject to change without notice
-- and should not be construed as a commitment by SNMP Research, Incorporated.
--
-- Restricted Rights Legend:
--  Use, duplication, or disclosure by the Government is subject to
--  restrictions as set forth in subparagraph (c)(1)(ii) of the Rights
--  in Technical Data and Computer Software clause at DFARS 252.227-7013;
--  subparagraphs (c)(4) and (d) of the Commercial Computer
--  Software-Restricted Rights Clause, FAR 52.227-19; and in similar
--  clauses in the NASA FAR Supplement and other corresponding
--  governmental regulations.
--
--

--
--                PROPRIETARY NOTICE
--
-- This software is an unpublished work subject to a confidentiality agreement
-- and is protected by copyright and trade secret law.  Unauthorized copying,
-- redistribution or other use of this work is prohibited.
--
-- The above notice of copyright on this source code product does not indicate
-- any actual or intended publication of such source code.
--

   SIMPLE-POLICY-PRO-CDISTRIB-MIB DEFINITIONS ::= BEGIN

   IMPORTS
       MODULE-IDENTITY, NOTIFICATION-TYPE
           FROM SNMPv2-SMI;

   snmpResearch                OBJECT IDENTIFIER ::= { enterprises 99 }

   secureIntelligence          OBJECT IDENTIFIER ::= { snmpResearch 16 }

   enterpol                    OBJECT IDENTIFIER ::= { secureIntelligence 1 }

   enterpolEvents              OBJECT IDENTIFIER ::= { enterpol 1 }

   enterpolCdistribEvents      OBJECT IDENTIFIER ::= { enterpolEvents 2 }

   enterpolSimplePolicyProCdistribEvents MODULE-IDENTITY
       LAST-UPDATED "200109241025Z"
       ORGANIZATION "SNMP Research"
       CONTACT-INFO
              " Postal: SNMP Research
                        3001 Kimberlin Heights Road
                        Knoxville, TN  37920-9716

                   Tel: +1 865 573 1434
                   Fax: +1 865 573 9197

                E-mail: info@snmp.com"

       DESCRIPTION
               "Events of the Configuration Distributor Subsystem
               of EnterPol related to Simple PolicyPro."
       ::= { enterpolCdistribEvents 1 }

   sppCdAllNeededInfoInTpDb NOTIFICATION-TYPE
       STATUS        current
       DESCRIPTION
               ""
       ::= { enterpolSimplePolicyProCdistribEvents 1 }

   sppCdDoneWithTidSoPurgeTpDb NOTIFICATION-TYPE
       STATUS        current
       DESCRIPTION
               ""
       ::= { enterpolSimplePolicyProCdistribEvents 2 }

   sppCdTidCompletelyFailed NOTIFICATION-TYPE
       STATUS        current
       DESCRIPTION
               ""
       ::= { enterpolSimplePolicyProCdistribEvents 3 }

   sppCdConflictQuestion NOTIFICATION-TYPE
       STATUS        current
       DESCRIPTION
               ""
       ::= { enterpolSimplePolicyProCdistribEvents 4 }

   sppCdTimedRetry NOTIFICATION-TYPE
       STATUS        current
       DESCRIPTION
               ""
       ::= { enterpolSimplePolicyProCdistribEvents 5 }

   sppCdRetryEventScheduled NOTIFICATION-TYPE
       STATUS        current
       DESCRIPTION
               ""
       ::= { enterpolSimplePolicyProCdistribEvents 6 }

   sppCdCouldNotRemoveConflict NOTIFICATION-TYPE
       STATUS        current
       DESCRIPTION
               ""
       ::= { enterpolSimplePolicyProCdistribEvents 7 }

   sppCdFailureOnDevice NOTIFICATION-TYPE
       STATUS        current
       DESCRIPTION
               ""
       ::= { enterpolSimplePolicyProCdistribEvents 8 }

   sppCdSuccessOnDevice NOTIFICATION-TYPE
       STATUS        current
       DESCRIPTION
               ""
       ::= { enterpolSimplePolicyProCdistribEvents 9 }

   sppCdInvalidRetryValues NOTIFICATION-TYPE
       STATUS        current
       DESCRIPTION
               ""
       ::= { enterpolSimplePolicyProCdistribEvents 10 }

   sppCdInternalError NOTIFICATION-TYPE
       STATUS        current
       DESCRIPTION
               ""
       ::= { enterpolSimplePolicyProCdistribEvents 21 }

   sppCdNoResponseVarbindList NOTIFICATION-TYPE
       STATUS        current
       DESCRIPTION
               ""
       ::= { enterpolSimplePolicyProCdistribEvents 22 }

   sppCdUnexpectedResponseVarbindList NOTIFICATION-TYPE
       STATUS        current
       DESCRIPTION
               ""
       ::= { enterpolSimplePolicyProCdistribEvents 23 }

   sppCdResponseVarbindListContainsWrongType NOTIFICATION-TYPE
       STATUS        current
       DESCRIPTION
               ""
       ::= { enterpolSimplePolicyProCdistribEvents 24 }

   sppCdResponseVarbindListContainsBadValue NOTIFICATION-TYPE
       STATUS        current
       DESCRIPTION
               ""
       ::= { enterpolSimplePolicyProCdistribEvents 25 }

   sppCdDatabaseAccessFunctionFailed NOTIFICATION-TYPE
       STATUS        current
       DESCRIPTION
               ""
       ::= { enterpolSimplePolicyProCdistribEvents 26 }

   sppCdGetSidFailed NOTIFICATION-TYPE
       STATUS        current
       DESCRIPTION
               ""
       ::= { enterpolSimplePolicyProCdistribEvents 27 }

   sppCdInvalidCommandString NOTIFICATION-TYPE
       STATUS        current
       DESCRIPTION
               ""
       ::= { enterpolSimplePolicyProCdistribEvents 41 }

   sppCdMalformedCommandString NOTIFICATION-TYPE
       STATUS        current
       DESCRIPTION
               ""
       ::= { enterpolSimplePolicyProCdistribEvents 42 }

   sppCdInvalidNetworkAddress NOTIFICATION-TYPE
       STATUS        current
       DESCRIPTION
               ""
       ::= { enterpolSimplePolicyProCdistribEvents 43 }

   sppCdNoAgents NOTIFICATION-TYPE
       STATUS        current
       DESCRIPTION
               ""
       ::= { enterpolSimplePolicyProCdistribEvents 44 }

   sppCdNoPolicyPackages NOTIFICATION-TYPE
       STATUS        current
       DESCRIPTION
               ""
       ::= { enterpolSimplePolicyProCdistribEvents 45 }

   sppCdNoPolicies NOTIFICATION-TYPE
       STATUS        current
       DESCRIPTION
               ""
       ::= { enterpolSimplePolicyProCdistribEvents 46 }

   sppCdNoUsers NOTIFICATION-TYPE
       STATUS        current
       DESCRIPTION
               ""
       ::= { enterpolSimplePolicyProCdistribEvents 47 }

   sppCdNoViews NOTIFICATION-TYPE
       STATUS        current
       DESCRIPTION
               ""
       ::= { enterpolSimplePolicyProCdistribEvents 48 }

   sppCdNoIncludedSubtress NOTIFICATION-TYPE
       STATUS        current
       DESCRIPTION
               ""
       ::= { enterpolSimplePolicyProCdistribEvents 49 }

   sppCdRemoveDuplicatesFailed NOTIFICATION-TYPE
       STATUS        current
       DESCRIPTION
               ""
       ::= { enterpolSimplePolicyProCdistribEvents 50 }

   sppCdRemoveDuplicatesCountInvalid NOTIFICATION-TYPE
       STATUS        current
       DESCRIPTION
               ""
       ::= { enterpolSimplePolicyProCdistribEvents 51 }

   sppCdCommandVerbNotImplemented NOTIFICATION-TYPE
       STATUS        current
       DESCRIPTION
               ""
       ::= { enterpolSimplePolicyProCdistribEvents 52 }

   sppCdUnknownCommandVerb NOTIFICATION-TYPE
       STATUS        current
       DESCRIPTION
               ""
       ::= { enterpolSimplePolicyProCdistribEvents 53 }

   sppCdNoOldPassword NOTIFICATION-TYPE
       STATUS        current
       DESCRIPTION
               ""
       ::= { enterpolSimplePolicyProCdistribEvents 54 }

   sppCdNoManagers NOTIFICATION-TYPE
       STATUS        current
       DESCRIPTION
               ""
       ::= { enterpolSimplePolicyProCdistribEvents 55 }

   sppCdRemoveSolosFailed NOTIFICATION-TYPE
       STATUS        current
       DESCRIPTION
               ""
       ::= { enterpolSimplePolicyProCdistribEvents 56 }

   sppCdCheckingNumberOfOccurrences NOTIFICATION-TYPE
       STATUS        current
       DESCRIPTION
               ""
       ::= { enterpolSimplePolicyProCdistribEvents 57 }

   sppCdInvalidContextPrefix NOTIFICATION-TYPE
       STATUS        current
       DESCRIPTION
               ""
       ::= { enterpolSimplePolicyProCdistribEvents 61 }

   sppCdUnexpectedContextPrefix NOTIFICATION-TYPE
       STATUS        current
       DESCRIPTION
               ""
       ::= { enterpolSimplePolicyProCdistribEvents 62 }

   sppCdInvalidAccess NOTIFICATION-TYPE
       STATUS        current
       DESCRIPTION
               ""
       ::= { enterpolSimplePolicyProCdistribEvents 63 }

   sppCdUnknownAccess NOTIFICATION-TYPE
       STATUS        current
       DESCRIPTION
               ""
       ::= { enterpolSimplePolicyProCdistribEvents 64 }

   sppCdInvalidSecurityLevel NOTIFICATION-TYPE
       STATUS        current
       DESCRIPTION
               ""
       ::= { enterpolSimplePolicyProCdistribEvents 65 }

   sppCdUnknownSecurityLevel NOTIFICATION-TYPE
       STATUS        current
       DESCRIPTION
               ""
       ::= { enterpolSimplePolicyProCdistribEvents 66 }

   sppCdRowCreationFailedVacmAccessTable NOTIFICATION-TYPE
       STATUS        current
       DESCRIPTION
               ""
       ::= { enterpolSimplePolicyProCdistribEvents 67 }

   sppCdRowDeletionFailedVacmAccessTable NOTIFICATION-TYPE
       STATUS        current
       DESCRIPTION
               ""
       ::= { enterpolSimplePolicyProCdistribEvents 68 }

   sppCdInvalidPolicy NOTIFICATION-TYPE
       STATUS        current
       DESCRIPTION
               ""
       ::= { enterpolSimplePolicyProCdistribEvents 69 }

   sppCdInvalidView NOTIFICATION-TYPE
       STATUS        current
       DESCRIPTION
               ""
       ::= { enterpolSimplePolicyProCdistribEvents 70 }

   sppCdRowModificationFailedVacmAccessTable NOTIFICATION-TYPE
       STATUS        current
       DESCRIPTION
               ""
       ::= { enterpolSimplePolicyProCdistribEvents 71 }

   sppCdCouldNotGetViewSpinLock NOTIFICATION-TYPE
       STATUS        current
       DESCRIPTION
               ""
       ::= { enterpolSimplePolicyProCdistribEvents 81 }

   sppCdRowCreationFailedVacmViewTreeFamilyTable NOTIFICATION-TYPE
       STATUS        current
       DESCRIPTION
               ""
       ::= { enterpolSimplePolicyProCdistribEvents 82 }

   sppCdRowDeletionFailedVacmViewTreeFamilyTable NOTIFICATION-TYPE
       STATUS        current
       DESCRIPTION
               ""
       ::= { enterpolSimplePolicyProCdistribEvents 83 }

   sppCdCouldNotTranslateOidForSubtree NOTIFICATION-TYPE
       STATUS        current
       DESCRIPTION
               ""
       ::= { enterpolSimplePolicyProCdistribEvents 84 }

   sppCdCouldNotGetEngineId NOTIFICATION-TYPE
       STATUS        current
       DESCRIPTION
               ""
       ::= { enterpolSimplePolicyProCdistribEvents 101 }

   sppCdCouldNotGetUserSecurityName NOTIFICATION-TYPE
       STATUS        current
       DESCRIPTION
               ""
       ::= { enterpolSimplePolicyProCdistribEvents 121 }

   sppCdRowCreationFailedVacmSecToGroupTable NOTIFICATION-TYPE
       STATUS        current
       DESCRIPTION
               ""
       ::= { enterpolSimplePolicyProCdistribEvents 122 }

   sppCdRowDeletionFailedVacmSecToGroupTable NOTIFICATION-TYPE
       STATUS        current
       DESCRIPTION
               ""
       ::= { enterpolSimplePolicyProCdistribEvents 123 }

   sppCdCouldNotGetUserSpinLock NOTIFICATION-TYPE
       STATUS        current
       DESCRIPTION
               ""
       ::= { enterpolSimplePolicyProCdistribEvents 141 }

   sppCdNoAuthinfoDataForUser NOTIFICATION-TYPE
       STATUS        current
       DESCRIPTION
               ""
       ::= { enterpolSimplePolicyProCdistribEvents 142 }

   sppCdInsufficientCloneFromSecurityLevel NOTIFICATION-TYPE
       STATUS        current
       DESCRIPTION
               ""
       ::= { enterpolSimplePolicyProCdistribEvents 143 }

   sppCdInconsistentAuthParameters NOTIFICATION-TYPE
       STATUS        current
       DESCRIPTION
               ""
       ::= { enterpolSimplePolicyProCdistribEvents 144 }

   sppCdUnknownAuthProtocol NOTIFICATION-TYPE
       STATUS        current
       DESCRIPTION
               ""
       ::= { enterpolSimplePolicyProCdistribEvents 145 }

   sppCdNoAuthKey NOTIFICATION-TYPE
       STATUS        current
       DESCRIPTION
               ""
       ::= { enterpolSimplePolicyProCdistribEvents 146 }

   sppCdInconsistentPrivParameters NOTIFICATION-TYPE
       STATUS        current
       DESCRIPTION
               ""
       ::= { enterpolSimplePolicyProCdistribEvents 147 }

   sppCdUnknownPrivProtocol NOTIFICATION-TYPE
       STATUS        current
       DESCRIPTION
               ""
       ::= { enterpolSimplePolicyProCdistribEvents 148 }

   sppCdNoPrivKey NOTIFICATION-TYPE
       STATUS        current
       DESCRIPTION
               ""
       ::= { enterpolSimplePolicyProCdistribEvents 149 }

   sppCdRowCreationFailedUsmUserTable NOTIFICATION-TYPE
       STATUS        current
       DESCRIPTION
               ""
       ::= { enterpolSimplePolicyProCdistribEvents 150 }

   sppCdCouldNotGetUserProtocols NOTIFICATION-TYPE
       STATUS        current
       DESCRIPTION
               ""
       ::= { enterpolSimplePolicyProCdistribEvents 151 }

   sppCdUnknownAuthProtocolFromAgent NOTIFICATION-TYPE
       STATUS        current
       DESCRIPTION
               ""
       ::= { enterpolSimplePolicyProCdistribEvents 152 }

   sppCdUnknownPrivProtocolFromAgent NOTIFICATION-TYPE
       STATUS        current
       DESCRIPTION
               ""
       ::= { enterpolSimplePolicyProCdistribEvents 153 }

   sppCdCouldNotChangePassword NOTIFICATION-TYPE
       STATUS        current
       DESCRIPTION
               ""
       ::= { enterpolSimplePolicyProCdistribEvents 154 }

   sppCdRowDeletionFailedUsmUserTable NOTIFICATION-TYPE
       STATUS        current
       DESCRIPTION
               ""
       ::= { enterpolSimplePolicyProCdistribEvents 155 }

   sppCdCouldNotVerifyClonefromUser NOTIFICATION-TYPE
       STATUS        current
       DESCRIPTION
               ""
       ::= { enterpolSimplePolicyProCdistribEvents 156 }

   sppCdClonefromUserNotActive NOTIFICATION-TYPE
       STATUS        current
       DESCRIPTION
               ""
       ::= { enterpolSimplePolicyProCdistribEvents 157 }

   sppCdRowCreationFailedCommunityTable NOTIFICATION-TYPE
       STATUS        current
       DESCRIPTION
               ""
       ::= { enterpolSimplePolicyProCdistribEvents 161 }

   sppCdRowDeletionFailedCommunityTable NOTIFICATION-TYPE
       STATUS        current
       DESCRIPTION
               ""
       ::= { enterpolSimplePolicyProCdistribEvents 162 }

   sppCdRowCreationFailedSnmpNotifyTable NOTIFICATION-TYPE
       STATUS        current
       DESCRIPTION
               ""
       ::= { enterpolSimplePolicyProCdistribEvents 171 }

   sppCdRowDeletionFailedSnmpNotifyTable NOTIFICATION-TYPE
       STATUS        current
       DESCRIPTION
               ""
       ::= { enterpolSimplePolicyProCdistribEvents 172 }

   sppCdRowCreationFailedTargetAddrTable NOTIFICATION-TYPE
       STATUS        current
       DESCRIPTION
               ""
       ::= { enterpolSimplePolicyProCdistribEvents 173 }

   sppCdRowDeletionFailedTargetAddrTable NOTIFICATION-TYPE
       STATUS        current
       DESCRIPTION
               ""
       ::= { enterpolSimplePolicyProCdistribEvents 174 }

   sppCdRowCreationFailedTargetParamsTable NOTIFICATION-TYPE
       STATUS        current
       DESCRIPTION
               ""
       ::= { enterpolSimplePolicyProCdistribEvents 175 }

   sppCdRowDeletionFailedTargetParamsTable NOTIFICATION-TYPE
       STATUS        current
       DESCRIPTION
               ""
       ::= { enterpolSimplePolicyProCdistribEvents 176 }

END

COMMUNITY-MIB DEFINITIONS ::= BEGIN

    IMPORTS
        MODULE-IDENTITY, OBJECT-TYPE, Integer32, Counter32, UInteger32
            FROM SNMPv2-SMI
        RowStatus, TestAndIncr
             FROM SNMPv2-TC
        MemoryType, TransportLabel, AuthName, SnmpID
             FROM V2ADMIN-MIB
        MODULE-COMPLIANCE, OBJECT-GROUP
            FROM SNMPv2-CONF;

    communityMIB MODULE-IDENTITY
        LAST-UPDATED "9508121700"
        ORGANIZATION "IETF SNMPv2 Working Group"
        CONTACT-INFO
              "snmpv2@tis.com
              Full contact info to be provided . . ."
        DESCRIPTION
              "The MIB module for configuring SNMPv2 agents."
        ::= { snmpModules 1133 }

    --
    -- Spin lock for modification of the communityTable
    --

    communitySpinLock OBJECT-TYPE
        SYNTAX       TestAndIncr
        MAX-ACCESS   read-write
        STATUS       current
        DESCRIPTION
              "An advisory lock used to allow several cooperating SNMPv2
              entities, all acting in a manager role, to coordinate their
              use of SNMPv2 set operations to entries in the communityTable.
              A manager application should include the value of
              communitySpinLock in every set operation which accesses the
              communityTable.  Since this is an advisory lock, entities
              acting in an agent role do not enforce the use of
              communitySpinLock."
        ::= { communityMIB 1 }

    --
    -- The communityTable contains a database of community strings.
    -- This table provides mappings between a community string, and the











    -- parameters required for processing SNMPv2 messages.
    --
    -- Note that this table does not include an authSnmpID, as this
    -- value will always be equal to the snmpID object of the agent
    -- which implements the table.
    --

    communityTable OBJECT-TYPE
        SYNTAX       SEQUENCE OF CommunityEntry
        MAX-ACCESS   not-accessible
        STATUS       current
        DESCRIPTION
              "The database of community strings."
        ::= { communityMIB 2 }

    communityEntry OBJECT-TYPE
        SYNTAX       CommunityEntry
        MAX-ACCESS   not-accessible
        STATUS       current
        DESCRIPTION
              "Information about a particular community string."
        INDEX { communityAuthSnmpID, IMPLIED communityName }
        ::= { communityTable 1 }

    CommunityEntry ::= SEQUENCE {
        communityAuthSnmpID          SnmpID,
        communityName                AuthName,
        communityGroupName           AuthName,
        communityContextSnmpID       SnmpID,
        communityContextName         AuthName,
        communityTransportLabel      TransportLabel,
        communityMemoryType          MemoryType,
        communityStatus              RowStatus
    }

    communityAuthSnmpID OBJECT-TYPE
        SYNTAX       SnmpID
        MAX-ACCESS   read-create
        STATUS       current
        DESCRIPTION
              "The authSnmpID to which a community string maps. For
              non-proxy and incoming proxy community strings, this
              should always be equal to the local SNMPv2 entity's
              snmpID object.  For outgoing proxy community strings,
              this should be equal to the snmpID of the destination
              SNMPv2 entity."
        ::= { communityEntry 1 }

    communityName OBJECT-TYPE
        SYNTAX       OCTET STRING (SIZE(1..255))
        MAX-ACCESS   not-accessible
        STATUS       current
        DESCRIPTION
              "The community string for which a row in this table represents
              a configuration.  This value is also used as an identityName
              when mapping between community strings and identityNames."
        ::= { communityEntry 2 }

    communityGroupName OBJECT-TYPE
        SYNTAX       AuthName
        MAX-ACCESS   read-create
        STATUS       current
        DESCRIPTION
              "The SNMPv2 groupName to which a community string maps.
              This object is used to determine access rights for a
              community string through the acTable."
        ::= { communityEntry 3 }

    communityContextSnmpID OBJECT-TYPE
        SYNTAX       SnmpID
        MAX-ACCESS   read-create
        STATUS       current
        DESCRIPTION
              "The v2ContextSnmpID to which a community string maps.
              This object specifies the snmpID of the context in
              which management information is accessible to this community."
        ::= { communityEntry 4 }

    communityContextName OBJECT-TYPE
        SYNTAX       AuthName
        MAX-ACCESS   read-create
        STATUS       current
        DESCRIPTION
              "The v2ContextName to which a community string maps.
              This object specifies the context in which management
              information is accessible to this community."
        ::= { communityEntry 5 }

    communityTransportLabel OBJECT-TYPE
        SYNTAX       TransportLabel











        MAX-ACCESS   read-create
        STATUS       current
        DESCRIPTION
              "This object specifies a set of transport endpoints from which
              an agent will accept management requests.  If a management
              request containing this community is received on a transport
              endpoint other than the transport endpoints identified
              by this object, the request is deemed unauthentic.

              The transports identified by this object are specified in
              the transportTable.  Entries in the transportTable whose
              transportLabel value are equal to this object are identified.

              If the value of this object has zero-length, or if the
              transportTable is not implemented, then transport endpoints
              are not checked when authenticating messages containing
              this community string."
        ::= { communityEntry 6 }

    communityMemoryType OBJECT-TYPE
        SYNTAX       MemoryType
        MAX-ACCESS   read-create
        STATUS       current
        DESCRIPTION
              "The storage type for this conceptual row in the
              communityTable.  Conceptual rows having the value 'permanent'
              need not allow write-access to any columnar object in the
              row."
        ::= { communityEntry 7 }

    communityStatus OBJECT-TYPE
        SYNTAX       RowStatus
        MAX-ACCESS   read-create
        STATUS       current
        DESCRIPTION
              "The status of this conceptual row in the communityTable.

              An entry in this table is not qualified for activation
              until instance of all corresponding columns have been
              initialized, either through default values, or through
              Set operations."
        ::= { communityEntry 8 }














    v2AdminCommunityGroup OBJECT-GROUP
        OBJECTS {
                 communitySpinLock,
                 communityAuthSnmpID,
                 communityName,
                 communityGroupName,
                 communityContextSnmpID,
                 communityContextName,
                 communityTransportLabel,
                 communityMemoryType,
                 communityStatus
                }
        STATUS    current
        DESCRIPTION
              "A collection of objects providing for configuration of an
              SNMPv1 or SNMPv2c agent."
        ::= { v2AdminMIBGroups 6 }

END

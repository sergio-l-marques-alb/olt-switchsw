--
--
-- Copyright (C) 1996-2006 by SNMP Research, Incorporated.
--
-- This software is furnished under a license and may be used and copied
-- only in accordance with the terms of such license and with the
-- inclusion of the above copyright notice. This software or any other
-- copies thereof may not be provided or otherwise made available to any
-- other person. No title to and ownership of the software is hereby
-- transferred.
--
-- The information in this software is subject to change without notice
-- and should not be construed as a commitment by SNMP Research, Incorporated.
--
-- Restricted Rights Legend:
--  Use, duplication, or disclosure by the Government is subject to
--  restrictions as set forth in subparagraph (c)(1)(ii) of the Rights
--  in Technical Data and Computer Software clause at DFARS 252.227-7013;
--  subparagraphs (c)(4) and (d) of the Commercial Computer
--  Software-Restricted Rights Clause, FAR 52.227-19; and in similar
--  clauses in the NASA FAR Supplement and other corresponding
--  governmental regulations.
--
--
--
--                PROPRIETARY NOTICE
--
-- This software is an unpublished work subject to a confidentiality agreement
-- and is protected by copyright and trade secret law.  Unauthorized copying,
-- redistribution or other use of this work is prohibited.
--
-- The above notice of copyright on this source code product does not indicate
-- any actual or intended publication of such source code.
--
--

   RECONFIG-MIB DEFINITIONS ::= BEGIN

   IMPORTS
       MODULE-IDENTITY, OBJECT-TYPE
           FROM SNMPv2-SMI
       DisplayString, RowStatus
           FROM SNMPv2-TC
       srExperimentalMIBs
           FROM SNMP-RESEARCH-MIB;

   reconfigMIB MODULE-IDENTITY
       LAST-UPDATED "9611140000Z"
       ORGANIZATION "SNMP Research, Inc."
       CONTACT-INFO "
                  Postal Address:

                  SNMP Research, Inc
                  3001 Kimberlin Heights Rd.
                  Knoxville, TN 37920-9716
                  USA

                  Tel:     +1 865 573 1434
                  Fax:     +1 865 573 9197
                  E-mail:  info@.snmp.com
                  WWW:     http://www.snmp.com"
       DESCRIPTION
               "A MIB module to allow for dynamic reconfiguration of
                an SNMP Research agent."
       ::= { srExperimentalMIBs 2 }

   FileType ::= TEXTUAL-CONVENTION
       STATUS       current
       DESCRIPTION "The possible kinds of configuration files that
                    can be used for the reconfiguration.  At this
                    time, the only possibilities are a *info.dat
		    file and the snmpd.cnf file."
       SYNTAX       INTEGER {
		      noneOfTheBelow(1),
		      mibTreeFile(2),
		      snmpdCnfFile(3)
                    }

   ActionType ::= TEXTUAL-CONVENTION
       STATUS       current
       DESCRIPTION "The action that should be taken using a particular
		    file."
       SYNTAX       INTEGER {
		      noneOfTheBelow(1),
		      merge(2),
		      reload(3)
                    }

   StateType ::= TEXTUAL-CONVENTION
       STATUS       current
       DESCRIPTION "Used by a management application to determine what
                    status of a request for reconfiguration is."
       SYNTAX       INTEGER {
		      neverRun(1),
		      inProgress(2),
                      completed(3)
                    }

   ErrorType ::= TEXTUAL-CONVENTION
       STATUS       current
       DESCRIPTION "The kinds of errors that can occur during a
		    reconfiguration action."
       SYNTAX       INTEGER {
		      noError(1),
		      unspecifiedError(2),
		      noSuchFile(3),
		      permissionDenied(4),
		      syntaxError(5)
                    }

   reconfigAgent OBJECT IDENTIFIER ::= { reconfigMIB 1 }

   reconfigNextAvailableRow OBJECT-TYPE
       SYNTAX      Integer32
       MAX-ACCESS  read-only
       STATUS      current
       DESCRIPTION
                "This object provides the index of the next available
 		 row in the reconfigTable."
       ::= { reconfigAgent 1 }

   reconfigTable OBJECT-TYPE
       SYNTAX      SEQUENCE OF ReconfigEntry
       MAX-ACCESS  not-accessible
       STATUS      current
       DESCRIPTION 
               "Table of re-configuration requests.  The index value
		has significance in that a manager may schedule several
		reconfiguration operations at one time.  The agent will
		then do them in the order implied by the index, lowest
		values first.
		
		When a new row is created, the reconfiguration action is
		scheduled when the row becomes active(1)."
       ::= { reconfigAgent 2 }

   reconfigEntry OBJECT-TYPE
       SYNTAX      ReconfigEntry
       MAX-ACCESS  not-accessible
       STATUS      current
       DESCRIPTION 
               "An entry (conceptual row) in the reconfigTable."
       INDEX { reconfigIndex }
       ::= { reconfigTable 1 }

   ReconfigEntry ::= SEQUENCE {
       reconfigIndex        Integer32,
       reconfigFileType     FileType,        -- snmpinfo.dat or snmpd.cnf
       reconfigFromFile     DisplayString,   -- where the data is from
       reconfigAction       ActionType,      -- what to do
       reconfigState        StateType,       -- current state
       reconfigError        ErrorType,       -- what error, if any
       reconfigErrorMsg     DisplayString,   -- description of error
       reconfigStatus       RowStatus
   }

   reconfigIndex OBJECT-TYPE
       SYNTAX      Integer32
       MAX-ACCESS  not-accessible
       STATUS      current
       DESCRIPTION
               "Simple integer-valued index"
       ::= { reconfigEntry 1 }

   reconfigFileType OBJECT-TYPE
       SYNTAX      FileType
       MAX-ACCESS  read-create
       STATUS      current
       DESCRIPTION
               "The type of the file:  either for MIB tree information
	        or snmpd.cnf.  The DEFVAL is there so that magical
		things don't happen without the manager meaning for them
		to."
       DEFVAL { noneOfTheBelow }
       ::= { reconfigEntry 2 }

   reconfigFromFile OBJECT-TYPE
       SYNTAX      DisplayString
       MAX-ACCESS  read-create
       STATUS      current
       DESCRIPTION
               "The full path to the file which will be read when the
		reconfiguration action is taken.  If this object has the
		empty string when the action is initiated, the following
		will occur:
		
                - if the reconfigFileType is mibTreeFile(2), the agent
		  will re-read snmpinfo.dat from either /etc/srconf/mgr
		  or SR_MGR_CONF_DIR

                - if the reconfigFileType is snmpdCnfFile(3), the agent
		  will re-read snmpd.cnf from either /etc/srconf/agt
		  or SR_AGT_CONF_DIR
		"
       DEFVAL { ''h }
       ::= { reconfigEntry 3 }

   reconfigAction OBJECT-TYPE
       SYNTAX      ActionType
       MAX-ACCESS  read-create
       STATUS      current
       DESCRIPTION
	       "The action that the manager wishes to take upon a
	        particular file.  This value may only be set if
		
		- the row is active(1) and the value of reconfigState
		  is completed(3).

		or

		- the value of reconfigState is neverRun(1).  This is
		  only possible if a row has been created but is not yet
		  active(1), since the value of reconfigState is
		  immediately set to inProgress when the row becomes
		  active.

                or

		- if the instance of reconfigAction doesn't exist as
		  during row creation.

		If reconfigState is inProgress(2), a set will result
		in a inconsistentValue error.

		When reconfigAction is successfully set, the action is
		scheduled for the next time through the 'main loop' and
		the value of reconfigResult is set to inProgress(2)."
       DEFVAL { noneOfTheBelow } 
       ::= { reconfigEntry 4 }

   reconfigState OBJECT-TYPE
       SYNTAX      StateType
       MAX-ACCESS  read-only
       STATUS      current
       DESCRIPTION
               "The state of a reconfiguration action.  When
		reconfigAction is initiated either by a set operation
		or when the row becomes active, the value of this
		object is immediately set to inProgress(2).  When the
		action has completed, either with or without an error,
		it is set to completed(3)."
       DEFVAL { neverRun }
       ::= { reconfigEntry 5 }

  reconfigError OBJECT-TYPE
       SYNTAX      ErrorType
       MAX-ACCESS  read-only
       STATUS      current
       DESCRIPTION
               "The error status of a reconfiguration action."
       DEFVAL { noError }
       ::= { reconfigEntry 6 }

  reconfigErrorMsg OBJECT-TYPE
       SYNTAX      DisplayString
       MAX-ACCESS  read-only
       STATUS      current
       DESCRIPTION
               "A textual string explaining the error."
       DEFVAL { ''h }
       ::= { reconfigEntry 7 }

  reconfigStatus OBJECT-TYPE
       SYNTAX      RowStatus
       MAX-ACCESS  read-create
       STATUS      current
       DESCRIPTION
               "The status of this conceptual row in the reconfigTable.

		The row is not qualified for activation if either 
		reconfigFileType or reconfigAction has the value
		noneOfTheBelow(1)."
       REFERENCE "See SNMPv2-TC for definition of RowStatus"
       ::= { reconfigEntry 8 }

loadSubagent  OBJECT IDENTIFIER ::= { reconfigMIB 2 }

-- We need a MIB for remotely loading a shared library Subagent.  This
-- currently doesn't exist.

END

XYPLEX MINIMAL MIB            21 Oct 91
            
            
            
            
                         Definitions of Minimal Managed Objects
                               for Xyplex Terminal Servers
            
                                     21 October 1991
            
                            Xyplex Document Number 420-0333-B
            
                                       Xyplex, Inc.
                                  330 Codman Hill Road
                                  Boxborough, MA 01719
            
                                     (508) 264-9900
            
                                   support@xyplex.com
            
            
            1.  Status of this Memo
            
            This document is submitted to the Internet MIB repository 
            and to Xyplex users as a Xyplex private extension to the 
            SNMP MIB.  Distribution of this memo is unlimited.  Please 
            express comments to Xyplex.
            
            2.  Abstract
            
            This memo defines a private portion of the Management 
            Information Base (MIB), within the Xyplex branch, for use 
            with SNMP over various transport services, such as UDP or 
            Ethernet.  In particular, it defines objects for minimal 
















            
            
            Xyplex                                            [Page   1]
            
            
            
                               XYPLEX MINIMAL MIB            21 Oct 91
            
            
            
            management of a Xyplex terminal server.
            
            This memo does not specify a standard for the Internet 
            community.  It describes an implementation in certain Xyplex 
            products.









































            
            
            Xyplex                                            [Page   2]
            
            
            
                               XYPLEX MINIMAL MIB            21 Oct 91
            
            
            
            3.  Historical Perspective
            
            As reported in RFC 1052, IAB Recommendations for the 
            Development of Internet Network Management Standards [1], a 
            two-prong strategy for network management of TCP/IP-based 
            internets was undertaken.  In the short-term, the Simple 
            Network Management Protocol (SNMP), defined in RFC 1067, was 
            to be used to manage nodes in the Internet community.  In 
            the long-term, the use of the OSI network management 
            framework was to be examined.  Two documents were produced 
            to define the management information: RFC 1065, which 
            defined the Structure of Management Information (SMI), and 
            RFC 1066, which defined the Management Information Base 
            (MIB).  Both of these documents were designed so as to be 
            compatible with both the SNMP and the OSI network management 
            framework.
            
            This strategy was quite successful in the short-term: 
            Internet-based network management technology was fielded, by 
            both the research and commercial communities, within a few 
            months.  As a result of this, portions of the Internet 
            community became network manageable in a timely fashion.
            
            As reported in RFC 1109, Report of the Second Ad Hoc Network 
            Management Review Group [2], the requirements of the SNMP 
            and the OSI network management frameworks were more 
            different than anticipated.  As such, the requirement for 
            compatibility between the SMI/MIB and both frameworks was 
            suspended.  This action permitted the operational network 
            management framework, based on the SNMP, to respond to new 
            operational needs in the Internet community by producing 
            MIB-II.
            
            In May of 1990, the core documents were elevated to 
            "Standard Protocols" with "Recommended" status.  As such, 
            the Internet- standard network management framework consists 
            of: Structure and Identification of Management Information 
            for TCP/IP-based internets, RFC 1155 [4], which describes 
            how managed objects contained in the MIB are defined; 
            Management Information Base for Network Management of 
            TCP/IP-based internets, which describes the managed objects 
            contained in the MIB, RFC 1156 [5]; and, the Simple Network 
            Management Protocol, RFC 1157 [6], which defines the 
            protocol used to manage these objects.
            
            Consistent with the IAB directive to produce simple, 

            
            
            Xyplex                                            [Page   3]
            
            
            
                               XYPLEX MINIMAL MIB            21 Oct 91
            
            
            
            workable systems in the short-term, the list of managed 
            objects defined in the Internet-standard MIB was derived by 
            taking only those elements which are considered essential.  
            However, the SMI defined three extensibility mechanisms: 
            one, the addition of new standard objects through the 
            definitions of new versions of the MIB; two, the addition of 
            widely-available but non- standard objects through the 
            experimental subtree; and three, the addition of private 
            objects through the enterprises subtree.  Such additional 
            objects can not only be used for vendor-specific elements, 
            but also for experimentation as required to further the 
            knowledge of which other objects are essential.
            
            This memo defines extensions to the MIB using the third 
            method.  It contains definitions of managed objects in 
            various Xyplex products as specified in [10].






























            
            
            Xyplex                                            [Page   4]
            
            
            
                               XYPLEX MINIMAL MIB            21 Oct 91
            
            
            
            4.  Objects
            
            Managed objects are accessed via a virtual information 
            store, termed the Management Information Base or MIB.  
            Objects in the MIB are defined using the subset of Abstract 
            Syntax Notation One (ASN.1) [7] defined in the SMI.  In 
            particular, each object has a name, a syntax, and an 
            encoding.  The name is an object identifier, an 
            administratively assigned name, which specifies an object 
            type.  The object type together with an object instance 
            serves to uniquely identify a specific instantiation of the 
            object.  For human convenience, we often use a textual 
            string, termed the OBJECT DESCRIPTOR, to also refer to the 
            object type.
            
            The syntax of an object type defines the abstract data 
            structure corresponding to that object type.  The ASN.1 
            language is used for this purpose.  However, the SMI [4] 
            purposely restricts the ASN.1 constructs which may be used. 
            These restrictions are explicitly made for simplicity.
            
            The encoding of an object type is simply how that object 
            type is represented using the object type's syntax.  
            Implicitly tied to the notion of an object type's syntax and 
            encoding is how the object type is represented when being 
            transmitted on the network.
            
            The SMI specifies the use of the basic encoding rules of 
            ASN.1 [8], subject to the additional requirements imposed by 
            the SNMP.
            
            
            4.1.  Format of Definitions
            
            Section 6 contains the specification of all object types 
            contained in this MIB module.  The object types are defined 
            using the conventions defined in the SMI, as amended by the 
            extensions specified in [9].








            
            
            Xyplex                                            [Page   5]
            
            
            
                               XYPLEX MINIMAL MIB            21 Oct 91
            
            
            
            5.  Overview
            
            The Xyplex Minimal MIB applies to Xyplex systems with 
            terminal ports, such as a terminal server.  It contains 
            relatively few objects, selected as those most important for 
            management of a terminal port.  Future Xyplex products are 
            expected to have considerably expanded MIBs.
            
            The MIB comprises three groups of information:  the System 
            group, the Character group, and the Internet group.  As a 
            convenience for the reader, the following descriptions 
            contain lists of the objects in each group.
            
            The System group contains information common to all Xyplex 
            systems.  It contains one base object, namely:
            
                sysIdent
            
            The Character group contains information for the management 
            of character stream (that is, terminal or printer) ports.  
            It comprises one base object and three tables.  The Physical 
            Character Port table contains information for each physical 
            port.  The Physical Character Input Signal table contains 
            information on hardware connector input signals.  The 
            Physical Character Output Signal table contains information 
            on hardware connector output signals.
            
            The Character group base object is:
            
                charPhysNumber
            
            The objects composing a Physical Character Port entry are:
            
                charPhysIndex
                charPhysPortName
                charPhysAdminAccess
                charPhysOperAccess
                charPhysBits
                charPhysParity
                charPhysSpeed
                charPhysModemControl
                charPhysSignalType
                charPhysInSignalNumber
                charPhysOutSignalNumber
                charPhysFlowControl
                charPhysInFlow

            
            
            Xyplex                                            [Page   6]
            
            
            
                               XYPLEX MINIMAL MIB            21 Oct 91
            
            
            
                charPhysOutFlow
                charPhysInFlowState
                charPhysOutFlowState
                charPhysAutobaud
                charPhysInCharacters
                charPhysOutCharacters
                charPhysFramingErrors
                charPhysParityErrors
                charPhysOverrunErrors
                charPhysLastInCharacter
                charPhysLastOutCharacter
                charPhysNode
                charPhysUserName
            
            The objects composing a Physical Character Input Signal 
            entry are:
            
                charInPhysIndex
                charInSignalName
                charInSignalState
            
            The objects composing a Physical Character Output Signal 
            entry are:
            
                charOutPhysIndex
                charOutSignalName
                charOutSignalState
            
            The Internet group contains information for the system's 
            Internet connection, where such information is not available 
            from the standard SNMP MIB.  It comprises several base 
            objects, namely:
            
                intDomainSuffix
                intDomainAddress1
                intDomainAddress2
                intGatewayAddress1
                intGatewayAddress2








            
            
            Xyplex                                            [Page   7]
            
            
            
                               XYPLEX MINIMAL MIB            21 Oct 91
            
            
            
            6.  Definitions
            
                    XYPLEX-MIB DEFINITIONS ::= BEGIN
            
                    IMPORTS
                            enterprises, Counter, TimeTicks
                                    FROM RFC1155-SMI
                            DisplayString
                                    FROM RFC1158-MIB
                            OBJECT-TYPE
                                    FROM RFC-oooo;
            
            xyplex          OBJECT IDENTIFIER ::= { enterprises 33 }
            system          OBJECT IDENTIFIER ::= { xyplex 1 }
            character       OBJECT IDENTIFIER ::= { xyplex 2 }
            xInternet       OBJECT IDENTIFIER ::= { xyplex 4 }
            
            --  This MIB module uses the extended OBJECT-TYPE macro as
            --  defined in [9]
            
            --  this is the private MIB module for Xyplex systems

























            
            
            Xyplex                                            [Page   8]
            
            
            
                               XYPLEX MINIMAL MIB            21 Oct 91
            
            
            
            -- the System group
            
            -- Implementation of this group is mandatory for all Xyplex
            -- systems
            
            sysIdent OBJECT-TYPE
                SYNTAX DisplayString (SIZE (0..40))
                ACCESS read-only
                STATUS mandatory
                DESCRIPTION
                    "An identification string for local and remote 
                    server displays.  Corresponds directly to SERVER 
                    IDENTIFICATION and the value labeled 
                    'Identification:' on the SERVER CHARACTERISTICS 
                    display."
                ::= { system 1 }






























            
            
            Xyplex                                            [Page   9]
            
            
            
                               XYPLEX MINIMAL MIB            21 Oct 91
            
            
            
            -- the Character group
            
            -- Implementation of this group is mandatory for all Xyplex
            -- systems with character stream physical ports
            
            charPhysNumber OBJECT-TYPE
                SYNTAX INTEGER
                ACCESS read-only
                STATUS mandatory
                DESCRIPTION
                    "The number of physical character (terminal) ports 
                    (regardless of their current state) present on this 
                    system."
                ::= { character 1 }
            































            
            
            Xyplex                                            [Page  10]
            
            
            
                               XYPLEX MINIMAL MIB            21 Oct 91
            
            
            
            -- the Physical Character Port table
            
            charPhysTable OBJECT-TYPE
                SYNTAX SEQUENCE OF CharPhysEntry
                ACCESS not-accessible
                STATUS mandatory
                DESCRIPTION
                    "A list of physical character port entries.  The 
                    number of entries is given by the value of 
                    charPhysNumber."
                ::= { character 2 }
            
            charPhysEntry OBJECT-TYPE
                SYNTAX CharPhysEntry
                ACCESS not-accessible
                STATUS mandatory
                DESCRIPTION
                    "Status and parameter values for a physical 
                    character port."
                INDEX { charPhysIndex }
                ::= { charPhysTable 1 }
            
            CharPhysEntry ::=
                SEQUENCE {
                    charPhysIndex
                        INTEGER,
                    charPhysPortName
                        DisplayString,
                    charPhysAdminAccess
                        INTEGER,
                    charPhysOperAccess
                        INTEGER,
                    charPhysBits
                        INTEGER,
                    charPhysParity
                        INTEGER,
                    charPhysSpeed
                        INTEGER,
                    charPhysModemControl
                        INTEGER,
                    charPhysSignalType
                        INTEGER,
                    charPhysInSignalNumber
                        INTEGER,
                    charPhysOutSignalNumber
                        INTEGER,

            
            
            Xyplex                                            [Page  11]
            
            
            
                               XYPLEX MINIMAL MIB            21 Oct 91
            
            
            
                    charPhysFlowControl
                        INTEGER,
                    charPhysInFlow
                        INTEGER,
                    charPhysOutFlow
                        INTEGER,
                    charPhysInFlowState
                        INTEGER,
                    charPhysOutFlowState
                        INTEGER,
                    charPhysAutobaud
                        INTEGER,
                    charPhysInCharacters
                        Counter,
                    charPhysOutCharacters
                        Counter,
                    charPhysFramingErrors
                        Counter,
                    charPhysParityErrors
                        Counter,
                    charPhysOverrunErrors
                        Counter,
                    charPhysLastInCharacter
                        INTEGER,
                    charPhysLastOutCharacter
                        INTEGER,
                    charPhysNode
                        DisplayString,
                    charPhysUserName
                        DisplayString
                }
            
            charPhysIndex OBJECT-TYPE
                SYNTAX INTEGER
                ACCESS read-only
                STATUS mandatory
                DESCRIPTION
                    "A unique value for each physical character port, 
                    directly corresponding to the physical connector.  
                    Its value ranges between 1 and the value of 
                    charPhysNumber."
                ::= { charPhysEntry 1 }
            
            charPhysPortName OBJECT-TYPE
                SYNTAX DisplayString (SIZE (0..16))
                ACCESS read-write

            
            
            Xyplex                                            [Page  12]
            
            
            
                               XYPLEX MINIMAL MIB            21 Oct 91
            
            
            
                STATUS mandatory
                DESCRIPTION
                    "An administratively-assigned name for the port.  If 
                    set to zero length, it becomes the standard, default 
                    name.  Corresponds directly to PORT NAME and the 
                    value labeled 'Name:' in the PORT CHARACTERISTICS 
                    display."
                ::= { charPhysEntry 2 }
            
            charPhysAdminAccess OBJECT-TYPE
                SYNTAX INTEGER { none(1), dynamic(2), local(3),
                                 remote(4) }
                ACCESS read-write
                STATUS mandatory
                DESCRIPTION
                    "The allowed mode of access to the port.  The value 
                    meanings are:
            
                    none       not accessed
                    dynamic    local or remote access
                    local      local access only
                    remote     remote access only
            
                    Corresponds directly to PORT ACCESS and the value 
                    labeled 'Access:' in the PORT CHARACTERISTICS 
                    display."
                ::= { charPhysEntry 3 }
            
            charPhysOperAccess OBJECT-TYPE
                SYNTAX INTEGER { none(1), local(3), remote(4) }
                ACCESS read-only
                STATUS mandatory
                DESCRIPTION
                    "The current mode of access to the port.
            
                    none       not accessed
                    local      local access
                    remote     remote access
            
                    Corresponds directly to the value labeled 'Access:' 
                    in the PORT STATUS display."
                ::= { charPhysEntry 4 }
            
            charPhysBits OBJECT-TYPE
                SYNTAX INTEGER (7..8)
                ACCESS read-write

            
            
            Xyplex                                            [Page  13]
            
            
            
                               XYPLEX MINIMAL MIB            21 Oct 91
            
            
            
                STATUS mandatory
                DESCRIPTION
                    "The port's number of bits per character.  
                    Corresponds directly to PORT CHARACTER SIZE and the 
                    value labeled 'Character Size:' in the PORT 
                    CHARACTERISTICS display."
                ::= { charPhysEntry 5 }
            
            charPhysParity OBJECT-TYPE
                SYNTAX INTEGER { none(1), even(2), mark(3), odd(4) }
                ACCESS read-write
                STATUS mandatory
                DESCRIPTION
                    "The type of character parity the port provides and 
                    expects.  The value meanings are:
            
                    none    ignored and not generated
                    even    an even number of 1s
                    mark    always 1
                    odd     an odd number of 1s
            
                    Corresponds directly to PORT PARITY and the value 
                    labeled 'Parity:' in the PORT CHARACTERISTICS 
                    display."
                ::= { charPhysEntry 6 }
            
            charPhysSpeed OBJECT-TYPE
                SYNTAX INTEGER
                ACCESS read-write
                STATUS mandatory
                DESCRIPTION
                    "The port's nominal bandwidth in bits per second.  
                    Corresponds directly to PORT SPEED and the value 
                    labeled 'Input Speed:' or 'Output Speed:' in the 
                    PORT CHARACTERISTICS display."
                ::= { charPhysEntry 7 }
            
            charPhysModemControl OBJECT-TYPE
                SYNTAX INTEGER { disabled(1), enabled(2) }
                ACCESS read-write
                STATUS mandatory
                DESCRIPTION
                    "A control to enable or disable observation of modem 
                    control signals.  Corresponds directly to PORT MODEM 
                    CONTROL and the value labeled 'Modem Control:' in 
                    the PORT CHARACTERISTICS display."

            
            
            Xyplex                                            [Page  14]
            
            
            
                               XYPLEX MINIMAL MIB            21 Oct 91
            
            
            
                ::= { charPhysEntry 8 }
            
            charPhysSignalType OBJECT-TYPE
                SYNTAX INTEGER { rs232(1), centronics(2),
                                 dataproducts(3) }
                ACCESS read-only
                STATUS mandatory
                DESCRIPTION
                    "The port's type of hardware interface.  For RS-232 
                    ports, this is assumed.  For parallel ports, it 
                    corresponds directly to the value labeled 'Printer 
                    Interface:' in the PORT STATUS display."
                ::= { charPhysEntry 9 }
            
            charPhysInSignalNumber OBJECT-TYPE
                SYNTAX INTEGER
                ACCESS read-only
                STATUS mandatory
                DESCRIPTION
                    "The number of hardware interface signals this port 
                    is capable of observing, indicating the number of 
                    entries for this port in charPhysInSignalTable.  
                    Corresponds directly to the possible values labeled 
                    'Input Signals:' in the PORT STATUS display."
                ::= { charPhysEntry 10 }
            
            charPhysOutSignalNumber OBJECT-TYPE
                SYNTAX INTEGER
                ACCESS read-only
                STATUS mandatory
                DESCRIPTION
                    "The number of hardware interface signals this port 
                    is capable of asserting, indicating the number of 
                    entries for this port in charPhysOutSignalTable.  
                    Corresponds directly to the possible values labeled 
                    'Output Signals:' in the PORT STATUS display."
                ::= { charPhysEntry 11 }
            
            charPhysFlowControl OBJECT-TYPE
                SYNTAX INTEGER { none(1), cts(2), dsr(3), xon(4) }
                ACCESS read-write
                STATUS mandatory
                DESCRIPTION
                    "The type of flow control the system applies to the 
                    port for input and output.  The value meanings are:
            

            
            
            Xyplex                                            [Page  15]
            
            
            
                               XYPLEX MINIMAL MIB            21 Oct 91
            
            
            
                    none    no flow control
                    cts     CTS/RTS
                    dsr     DCD/DTR/DSR
                    xon     XON/XOFF
            
                    Directly related to PORT FLOW CONTROL and the value 
                    labeled 'Flow Control:' in the PORT CHARACTERISTICS 
                    display."
                ::= { charPhysEntry 12 }
            
            charPhysInFlow OBJECT-TYPE
                SYNTAX INTEGER { disabled(1), enabled(2) }
                ACCESS read-write
                STATUS mandatory
                DESCRIPTION
                    "A control for application of flow control to 
                    characters coming into the port.  Corresponds 
                    directly to 'Input Flow Control' in the 'Enabled 
                    Characteristics' section of the PORT CHARACTERISTICS 
                    display."
                ::= { charPhysEntry 13 }
            
            charPhysOutFlow OBJECT-TYPE
                SYNTAX INTEGER { disabled(1), enabled(2) }
                ACCESS read-write
                STATUS mandatory
                DESCRIPTION
                    "A control for observation of flow control on 
                    characters going out of the port.  Corresponds 
                    directly to 'Output Flow Control' in the 'Enabled 
                    Characteristics' section of the PORT CHARACTERISTICS 
                    display."
                ::= { charPhysEntry 14 }
            
            charPhysInFlowState OBJECT-TYPE
                SYNTAX INTEGER { go(1), stop(2) }
                ACCESS read-only
                STATUS mandatory
                DESCRIPTION
                    "The dynamic state of flow control as applied by the 
                    system to characters coming into the port.  
                    Corresponds directly to the value labeled 'Input 
                    XOFFed:' in the PORT STATUS display."
                ::= { charPhysEntry 15 }
            
            charPhysOutFlowState OBJECT-TYPE

            
            
            Xyplex                                            [Page  16]
            
            
            
                               XYPLEX MINIMAL MIB            21 Oct 91
            
            
            
                SYNTAX INTEGER { go(1), stop(2) }
                ACCESS read-only
                STATUS mandatory
                DESCRIPTION
                    "The dynamic state of flow control as observed by 
                    the system on characters going out of the port.  
                    Corresponds directly to the value labeled 'Output 
                    XOFFed:' in the PORT STATUS display."
                ::= { charPhysEntry 16 }
            
            charPhysAutobaud OBJECT-TYPE
                SYNTAX INTEGER { disabled(1), enabled(2) }
                ACCESS read-write
                STATUS mandatory
                DESCRIPTION
                    "A control to allow the port to determine speed 
                    dynamically by looking for carriage return input 
                    characters.  Corresponds directly to 'Autobaud' in 
                    the 'Enabled Characteristics' section of the PORT 
                    CHARACTERISTICS display."
                ::= { charPhysEntry 17 }
            
            charPhysInCharacters OBJECT-TYPE
                SYNTAX Counter
                ACCESS read-only
                STATUS mandatory
                DESCRIPTION
                    "The total number of characters that have come into 
                    the port.  Corresponds directly to the value labeled 
                    'Input Count:' in the PORT COUNTERS display."
                ::= { charPhysEntry 18 }
            
            charPhysOutCharacters OBJECT-TYPE
                SYNTAX Counter
                ACCESS read-only
                STATUS mandatory
                DESCRIPTION
                    "The total number of characters that have gone out 
                    of the port.  Corresponds directly to the value 
                    labeled 'Output Count:' in the PORT COUNTERS 
                    display."
                ::= { charPhysEntry 19 }
            
            charPhysFramingErrors OBJECT-TYPE
                SYNTAX Counter
                ACCESS read-only

            
            
            Xyplex                                            [Page  17]
            
            
            
                               XYPLEX MINIMAL MIB            21 Oct 91
            
            
            
                STATUS mandatory
                DESCRIPTION
                    "The total number of characters that have come into 
                    the port with illegally formatted bit frames.  
                    Corresponds directly to the value labeled 'Framing 
                    Errors:' in the PORT COUNTERS display."
                ::= { charPhysEntry 20 }
            
            charPhysParityErrors OBJECT-TYPE
                SYNTAX Counter
                ACCESS read-only
                STATUS mandatory
                DESCRIPTION
                    "The total number of characters that have come into 
                    the port with invalid parity.  Corresponds directly 
                    to the value labeled 'Parity Errors:' in the PORT 
                    COUNTERS display."
                ::= { charPhysEntry 21 }
            
            charPhysOverrunErrors OBJECT-TYPE
                SYNTAX Counter
                ACCESS read-only
                STATUS mandatory
                DESCRIPTION
                    "The total number of characters coming into the port 
                    that the system lost due to no room in the port's 
                    input buffer.  Corresponds directly to the value 
                    labeled 'Overrun Errors:' in the PORT COUNTERS 
                    display."
                ::= { charPhysEntry 22 }
            
            charPhysLastInCharacter OBJECT-TYPE
                SYNTAX INTEGER (0..255)
                ACCESS read-only
                STATUS mandatory
                DESCRIPTION
                    "The character that most recently came into the 
                    port.  Corresponds directly to the value labeled 
                    'Last Char Input:' in the PORT STATUS display."
                ::= { charPhysEntry 23 }
            
            charPhysLastOutCharacter OBJECT-TYPE
                SYNTAX INTEGER (0..255)
                ACCESS read-only
                STATUS mandatory
                DESCRIPTION

            
            
            Xyplex                                            [Page  18]
            
            
            
                               XYPLEX MINIMAL MIB            21 Oct 91
            
            
            
                    "The character that most recently went out of the 
                    port.  Corresponds directly to the value labeled 
                    'Last Char Output:' in the PORT STATUS display."
                ::= { charPhysEntry 24 }
            
            charPhysNode OBJECT-TYPE
                SYNTAX DisplayString (SIZE (0..16))
                ACCESS read-only
                STATUS mandatory
                DESCRIPTION
                    "An identification for the network system with the 
                    current, active network connection to the port.  
                    Corresponds directly to the value labeled 'Current 
                    Node:' in the PORT STATUS display."
                ::= { charPhysEntry 25 }
            
            charPhysUserName OBJECT-TYPE
                SYNTAX DisplayString (SIZE (0..16))
                ACCESS read-only
                STATUS mandatory
                DESCRIPTION
                    "An identification of the user logged into the port 
                    on the current, active network connection to the 
                    port.  Corresponds directly to the value following 
                    'Port n:' in the PORT STATUS display."
                ::= { charPhysEntry 26 }




















            
            
            Xyplex                                            [Page  19]
            
            
            
                               XYPLEX MINIMAL MIB            21 Oct 91
            
            
            
            -- the Physical Character Input Signal table
            
            charPhysInSignalTable OBJECT-TYPE
                SYNTAX SEQUENCE OF CharPhysInSignalEntry
                ACCESS not-accessible
                STATUS mandatory
                DESCRIPTION
                    "A list of physical character port input hardware 
                    signal entries.  The number of entries is given by 
                    the value of charPhysInSignalNumber"
                ::= { character 3 }
            
            charPhysInSignalEntry OBJECT-TYPE
                SYNTAX CharPhysInSignalEntry
                ACCESS not-accessible
                STATUS mandatory
                DESCRIPTION
                    "A physical character port hardware signal entry 
                    containing objects for the particular signal on the 
                    particular port."
                INDEX { charInPhysIndex, charInSignalName }
                ::= { charPhysInSignalTable 1 }
            
            CharPhysInSignalEntry ::=
                SEQUENCE {
                    charInPhysIndex
                        INTEGER,
                    charInSignalName
                        DisplayString,
                    charInSignalState
                        INTEGER
                }
            
            charInPhysIndex OBJECT-TYPE
                SYNTAX INTEGER
                ACCESS read-only
                STATUS mandatory
                DESCRIPTION
                    "The index value that uniquely identifies the 
                    physical character port to which this signal 
                    belongs.  The port identified by a particular value 
                    of this index is the same port as identified by the 
                    same value of charPhysIndex."
                ::= { charPhysInSignalEntry 1 }
            
            -- The possible signal names for RS-232 signals are:  DCD,

            
            
            Xyplex                                            [Page  20]
            
            
            
                               XYPLEX MINIMAL MIB            21 Oct 91
            
            
            
            -- DTR, DSR, CTS, RTS, and RNG.
            
            -- The possible signal names for Centronics and Data
            -- Products signals are:  Fault, Power, PaperOut, Busy,
            -- and Online.
            
            charInSignalName OBJECT-TYPE
                SYNTAX DisplayString (SIZE (1..16))
                ACCESS read-only
                STATUS mandatory
                DESCRIPTION
                    "The name of the hardware signal, as appropriate to 
                    its type."
                ::= { charPhysInSignalEntry 2 }
            
            charInSignalState OBJECT-TYPE
                SYNTAX INTEGER  { on(1), off(2) }
                ACCESS read-only
                STATUS mandatory
                DESCRIPTION
                    "The current state of the signal.  For RS-232 ports, 
                    corresponds directly to the value labeled 'Input 
                    Signals:' in the PORT STATUS display.  For printer 
                    ports, corresponds to the various signal labels and 
                    values following the label 'Printer Interface:' in 
                    the PORT STATUS display."
                ::= { charPhysInSignalEntry 3 }
            


















            
            
            Xyplex                                            [Page  21]
            
            
            
                               XYPLEX MINIMAL MIB            21 Oct 91
            
            
            
            -- the Physical Character Output Signal table
            
            charPhysOutSignalTable OBJECT-TYPE
                SYNTAX SEQUENCE OF CharPhysOutSignalEntry
                ACCESS not-accessible
                STATUS mandatory
                DESCRIPTION
                    "A list of physical character port output hardware 
                    signal entries.  The number of entries is given by 
                    the value of charPhysOutSignalNumber"
                ::= { character 4 }
            
            charPhysOutSignalEntry OBJECT-TYPE
                SYNTAX CharPhysOutSignalEntry
                ACCESS not-accessible
                STATUS mandatory
                DESCRIPTION
                    "A physical character port hardware signal entry 
                    containing objects for the particular signal on the 
                    particular port."
                INDEX { charOutPhysIndex, charOutSignalName }
                ::= { charPhysOutSignalTable 1 }
            
            CharPhysOutSignalEntry ::=
                SEQUENCE {
                    charOutPhysIndex
                        INTEGER,
                    charOutSignalName
                        DisplayString,
                    charOutSignalState
                        INTEGER
                }
            
            charOutPhysIndex OBJECT-TYPE
                SYNTAX INTEGER
                ACCESS read-only
                STATUS mandatory
                DESCRIPTION
                    "The index value that uniquely identifies the 
                    physical character port to which this signal 
                    belongs.  The port identified by a particular value 
                    of this index is the same port as identified by the 
                    same value of charPhysIndex."
                ::= { charPhysOutSignalEntry 1 }
            
            -- The possible signal names for RS-232 signals are:  DCD,

            
            
            Xyplex                                            [Page  22]
            
            
            
                               XYPLEX MINIMAL MIB            21 Oct 91
            
            
            
            -- DTR, DSR, CTS, RTS, and RNG.
            
            -- The possible signal names for Centronics and Data
            -- Products signals are:  Fault, Power, PaperOut, Busy,
            -- and Online.
            
            charOutSignalName OBJECT-TYPE
                SYNTAX DisplayString (SIZE (1..16))
                ACCESS read-only
                STATUS mandatory
                DESCRIPTION
                    "The name of the hardware signal, as appropriate to 
                    its type."
                ::= { charPhysOutSignalEntry 2 }
            
            charOutSignalState OBJECT-TYPE
                SYNTAX INTEGER  { on(1), off(2) }
                ACCESS read-only
                STATUS mandatory
                DESCRIPTION
                    "The current state of the signal.  For RS-232 ports, 
                    corresponds directly to the value labeled 'Output 
                    Signals:' in the PORT STATUS display.  For printer 
                    ports, corresponds to the various signal labels and 
                    values following the label 'Printer Interface:' in 
                    the PORT STATUS display."
                ::= { charPhysOutSignalEntry 3 }



















            
            
            Xyplex                                            [Page  23]
            
            
            
                               XYPLEX MINIMAL MIB            21 Oct 91
            
            
            
            -- the Internet group
            
            -- Implementation of this group is mandatory for all Xyplex
            -- systems that implement Internet protocols
            
            intDomainSuffix OBJECT-TYPE
                SYNTAX DisplayString (SIZE (0..115))
                ACCESS read-write
                STATUS mandatory
                DESCRIPTION
                    "A partial domain name for the server to append to 
                    the end of an incomplete domain name provided by the 
                    user.  Corresponds directly to SERVER INTERNET 
                    DEFAULT DOMAIN SUFFIX and the value labeled 'Domain 
                    Suffix:' in the SERVER INTERNET CHARACTERISTICS 
                    display."
                ::= { xInternet 1 }
            
            intDomainAddress1 OBJECT-TYPE
                SYNTAX IpAddress
                ACCESS read-write
                STATUS mandatory
                DESCRIPTION
                    "The internet address of a Domain Name Server.  The 
                    system can use one or two such addresses, without 
                    preference.  A value of 0.0.0.0 indicates no 
                    address.  Corresponds directly to SERVER INTERNET 
                    PRIMARY DOMAIN ADDRESS and the value labeled 
                    'Primary Domain Address:' in the SERVER INTERNET 
                    CHARACTERISTICS display."
                ::= { xInternet 2 }
            
            intDomainAddress2 OBJECT-TYPE
                SYNTAX IpAddress
                ACCESS read-write
                STATUS mandatory
                DESCRIPTION
                    "The internet address of a Domain Name Server.  The 
                    system can use one or two such addresses, without 
                    preference.  A value of 0.0.0.0 indicates no 
                    address.  Corresponds directly to SERVER INTERNET 
                    SECONDARY DOMAIN ADDRESS and the value labeled 
                    'Secondary Domain Address:' in the SERVER INTERNET 
                    CHARACTERISTICS display."
                ::= { xInternet 3 }
            

            
            
            Xyplex                                            [Page  24]
            
            
            
                               XYPLEX MINIMAL MIB            21 Oct 91
            
            
            
            intGatewayAddress1 OBJECT-TYPE
                SYNTAX IpAddress
                ACCESS read-write
                STATUS mandatory
                DESCRIPTION
                    "The internet address of the system's primary (first 
                    choice) gateway.  A value of 0.0.0.0 indicates no 
                    address.  Corresponds directly to SERVER INTERNET 
                    PRIMARY GATEWAY ADDRESS and the value labeled 
                    'Primary Gateway Address:' in the SERVER INTERNET 
                    CHARACTERISTICS display."
                ::= { xInternet 4 }
            
            intGatewayAddress2 OBJECT-TYPE
                SYNTAX IpAddress
                ACCESS read-write
                STATUS mandatory
                DESCRIPTION
                    "The internet address of the system's secondary 
                    (second choice) gateway.  A value of 0.0.0.0 
                    indicates no address.  Corresponds directly to 
                    SERVER INTERNET SECONDARY GATEWAY ADDRESS and the 
                    value labeled 'Secondary Gateway Address:' in the 
                    SERVER INTERNET CHARACTERISTICS display."
                ::= { xInternet 5 }
            
            END



















            
            
            Xyplex                                            [Page  25]
            
            
            
                               XYPLEX MINIMAL MIB            21 Oct 91
            
            
            
            7.  References
            
            [1]  V. Cerf, IAB Recommendations for the Development of 
            Internet Network Management Standards.  Internet Working 
            Group Request for Comments 1052.  Network Information 
            Center, SRI International, Menlo Park, California, (April, 
            1988).
            
            [2]  V. Cerf, Report of the Second Ad Hoc Network Management 
            Review Group, Internet Working Group Request for Comments 
            1109.  Network Information Center, SRI International, Menlo 
            Park, California, (August, 1989).
            
            [3]  M.T. Rose (editor), Management Information Base for 
            Network Management of TCP/IP-based internets, Internet 
            Working Group Request for Comments 1158.  Network 
            Information Center, SRI International, Menlo Park, 
            California, (May, 1990).
            
            [4]  M.T. Rose and K. McCloghrie, Structure and 
            Identification of Management Information for TCP/IP-based 
            internets, Internet Working Group Request for Comments 1155. 
            Network Information Center, SRI International, Menlo Park, 
            California, (May, 1990).
            
            [5]  K. McCloghrie and M.T. Rose, Management Information 
            Base for Network Management of TCP/IP-based internets, 
            Internet Working Group Request for Comments 1156. Network 
            Information Center, SRI International, Menlo Park, 
            California, (May, 1990).
            
            [6]  J.D. Case, M.S. Fedor, M.L. Schoffstall, and J.R. 
            Davin, Simple Network Management Protocol, Internet Working 
            Group Request for Comments 1157.  Network Information 
            Center, SRI International, Menlo Park, California, (May, 
            1990).
            
            [7]  Information processing systems - Open Systems 
            Interconnection - Specification of Abstract Syntax Notation 
            One (ASN.1), International Organization for Standardization.  
            International Standard 8824, (December, 1987).
            
            [8]  Information processing systems - Open Systems 
            Interconnection - Specification of Basic Encoding Rules for 
            Abstract Notation One (ASN.1), International Organization 
            for Standardization.  International Standard 8825, 

            
            
            Xyplex                                            [Page  26]
            
            
            
                               XYPLEX MINIMAL MIB            21 Oct 91
            
            
            
            (December, 1987).
            
            [9] M.T. Rose, K. McCloghrie (editors), Towards Concise MIB 
            Definitions, Internet Draft, Internet Engineering Task 
            Force, (September, 1990).
            
            [10] B. Stewart, Xyplex MIB Extension Architectural 
            Specification, Xyplex document number 420-0332, 
            (4 September 1990).
            




































            
            
            Xyplex                                            [Page  27]

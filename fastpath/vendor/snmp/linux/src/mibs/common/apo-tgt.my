--
--
-- Copyright (C) 1999-2006 by SNMP Research, Incorporated.
--
-- This software is furnished under a license and may be used and copied
-- only in accordance with the terms of such license and with the
-- inclusion of the above copyright notice. This software or any other
-- copies thereof may not be provided or otherwise made available to any
-- other person. No title to and ownership of the software is hereby
-- transferred.
--
-- The information in this software is subject to change without notice
-- and should not be construed as a commitment by SNMP Research, Incorporated.
--
-- Restricted Rights Legend:
--  Use, duplication, or disclosure by the Government is subject to
--  restrictions as set forth in subparagraph (c)(1)(ii) of the Rights
--  in Technical Data and Computer Software clause at DFARS 252.227-7013;
--  subparagraphs (c)(4) and (d) of the Commercial Computer
--  Software-Restricted Rights Clause, FAR 52.227-19; and in similar
--  clauses in the NASA FAR Supplement and other corresponding
--  governmental regulations.
--
--

--
--                PROPRIETARY NOTICE
--
-- This software is an unpublished work subject to a confidentiality agreement
-- and is protected by copyright and trade secret law.  Unauthorized copying,
-- redistribution or other use of this work is prohibited.
--
-- The above notice of copyright on this source code product does not indicate
-- any actual or intended publication of such source code.
--


APO-TARGET-PARAMS-MIB DEFINITIONS ::= BEGIN

    IMPORTS
        apoModules
            FROM APO-CONSORTIUM-MIB
        MODULE-IDENTITY,
        OBJECT-TYPE
            FROM SNMPv2-SMI
        snmpTargetParamsEntry
            FROM SNMP-TARGET-MIB
        MODULE-COMPLIANCE,
        OBJECT-GROUP
            FROM SNMPv2-CONF;


    apoTargetParamsMIB MODULE-IDENTITY
        LAST-UPDATED "9801160000"
        ORGANIZATION "SNMP Research, Inc."
        CONTACT-INFO
                      ""
        DESCRIPTION
              ""
        ::= { apoModules 3 }



    apoTargetParamsMIBObjects OBJECT IDENTIFIER ::=
        { apoTargetParamsMIB 1 }
    apoTargetParamsMIBConformance OBJECT IDENTIFIER ::=
        { apoTargetParamsMIB 3 }

    --
    -- The apoTargetParamsTable
    --

    apoTargetParamsTable OBJECT-TYPE
        SYNTAX       SEQUENCE OF ApoTargetParamsEntry
        MAX-ACCESS   not-accessible
        STATUS       current
        DESCRIPTION
              "Table to add an APO version to the snmpTargetParamsTable."
        ::= { apoTargetParamsMIBObjects 1 }

    apoTargetParamsEntry OBJECT-TYPE
        SYNTAX       ApoTargetParamsEntry
        MAX-ACCESS   not-accessible
        STATUS       current
        DESCRIPTION
                   "Adds an APO version to the snmpTargetParamsEntry."
        AUGMENTS { snmpTargetParamsEntry }
        ::= { apoTargetParamsTable 1 }

    ApoTargetParamsEntry ::= SEQUENCE {
        apoTargetVersion     INTEGER
    }

    apoTargetVersion OBJECT-TYPE
        SYNTAX       INTEGER {
                         nonApo(0),
                         apoLevel1(1),
                         apoLevel2(2)
                     }
        MAX-ACCESS   read-create
        STATUS       current
        DESCRIPTION
              "This object is used to specify the APO version to be used
               when sending notifications to a corresponding target.

               If the apoTargetVersion defined for an snmpTargetParamsEntry
               cannot be supported by the notification target's security
               parameters as defined in the snmpTargetParamsEntry then the
               notification cannot be sent."
         DEFVAL { SNMPv2 }
        ::= { apoTargetParamsEntry 1 }

END

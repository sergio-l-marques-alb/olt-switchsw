YOUR-MIB DEFINITIONS ::= BEGIN

          IMPORTS
              MODULE-IDENTITY, OBJECT-TYPE, NOTIFICATION-TYPE,
              ObjectName, Integer32, Counter32, snmpModules
                  FROM SNMPv2-SMI
              TruthValue, DisplayString, TestAndIncr, TimeStamp
                  FROM SNMPv2-TC
              MODULE-COMPLIANCE, OBJECT-GROUP
                  FROM SNMPv2-CONF;

          --  Your MIB goes here 


          END

--
--
-- Copyright (C) 1996-2006 by SNMP Research, Incorporated.
--
-- This software is furnished under a license and may be used and copied
-- only in accordance with the terms of such license and with the
-- inclusion of the above copyright notice. This software or any other
-- copies thereof may not be provided or otherwise made available to any
-- other person. No title to and ownership of the software is hereby
-- transferred.
--
-- The information in this software is subject to change without notice
-- and should not be construed as a commitment by SNMP Research, Incorporated.
--
-- Restricted Rights Legend:
--  Use, duplication, or disclosure by the Government is subject to
--  restrictions as set forth in subparagraph (c)(1)(ii) of the Rights
--  in Technical Data and Computer Software clause at DFARS 252.227-7013;
--  subparagraphs (c)(4) and (d) of the Commercial Computer
--  Software-Restricted Rights Clause, FAR 52.227-19; and in similar
--  clauses in the NASA FAR Supplement and other corresponding
--  governmental regulations.
--
--

--
--                PROPRIETARY NOTICE
--
-- This software is an unpublished work subject to a confidentiality agreement
-- and is protected by copyright and trade secret law.  Unauthorized copying,
-- redistribution or other use of this work is prohibited.
--
-- The above notice of copyright on this source code product does not indicate
-- any actual or intended publication of such source code.
--
--
-- SNMP Research, Inc. grants permission to load this MIB onto your SNMP
-- management stations for use in configuring and managing LT-301 devices
-- and LATIN agents from SNMP Research.  SNMP Research, Inc. does not grant
-- permission to make additional copies, or distribute these MIBs to others
-- without written permission from SNMP Research, Inc.
--
--

LATIN-MIB DEFINITIONS ::= BEGIN

IMPORTS
    MODULE-IDENTITY, OBJECT-TYPE, NOTIFICATION-TYPE,
    ObjectName, Integer32, Counter32
        FROM SNMPv2-SMI;


latin MODULE-IDENTITY
    LAST-UPDATED "9707071615"
    ORGANIZATION "SNMP Research, Incorporated"
    CONTACT-INFO "SNMP Research, Incorporated
                  3001 Kimberlin Heights Road
                  Knoxville, Tennessee  37920-9716
                  U.S.A.
                  Voice:   +1-865-573-1434
                  FAX:     +1-865-573-9197
                  E-mail:  support@snmp.com"
    DESCRIPTION  "This MIB specifies objects for a general-purpose interface
                  between SNMP and character stream devices.  Example char-
                  acter stream devices are existing data processing equipment 
                  with serial communication (typically RS-232) ports."
::= { snmpResearchMIBs 21 }

snmpResearch                OBJECT IDENTIFIER ::= { enterprises 99 }
snmpResearchMIBs            OBJECT IDENTIFIER ::= { snmpResearch 12 }


--
--
-- The latinGeneralInfo Group
--
--

latinGeneralInfo OBJECT IDENTIFIER ::= { latin 1 }
 
latinDescr OBJECT-TYPE
    SYNTAX     DisplayString 
    MAX-ACCESS read-only
    STATUS     current
    DESCRIPTION "Specifies the type of LATIN agent; e.g., LISA, LT-301, etc.

                 The latinDescr can supply clues about LATIN agent capabil-
                 ities to SNMP management applications."
::= { latinGeneralInfo 1 }

latinNVStorage OBJECT-TYPE
    SYNTAX     INTEGER{
                   normal(1),
                   restoreLastConfig(2),
                   saveCurrentConfig(3),
                   restoreFactoryConfig(4)
                   } 
    MAX-ACCESS read-write
    STATUS     current
    DESCRIPTION "Commands the LATIN agent to save/retrieve the values of 
                 the LATIN MIB objects to/from non-volatile storage.

                 normal(1)               -  The default value always returned 
                                            when a set is not performed.

                 restoreLastConfig(2)    -  Restore the last saved 
                                            configuration.

                 saveCurrentConfig(3)    -  Save the current values of the 
                                            LATIN MIB objects in non-volatile 
                                            storage.

                 restoreFactoryConfig(4) -  Restore the factory default
                                            values for the LATIN MIB objects."
::= { latinGeneralInfo 2 }

--
--
-- The LATIN port table.
--
--

latinPortConfigTable OBJECT-TYPE
    SYNTAX     SEQUENCE OF LatinPortConfigEntry
    MAX-ACCESS not-accessible
    STATUS     current
    DESCRIPTION "The LATIN architecture allows one agent to support more than
                 one character stream device.

                 This table supplies descriptive and other information for
                 all character stream devices supported by a LATIN agent."
::= { latinGeneralInfo 3 }

latinPortConfigEntry OBJECT-TYPE
    SYNTAX     LatinPortConfigEntry
    MAX-ACCESS not-accessible
    STATUS     current
    DESCRIPTION "Describes a single character stream device."
    INDEX { latinPortIndex }
::= { latinPortConfigTable 1 }

LatinPortConfigEntry ::= SEQUENCE {
    latinPortIndex                         Integer32,
    latinPortDeviceDescr                   DisplayString,
    latinPortDeviceComment                 DisplayString,
    latinTrapPeriod                        Integer32,
    latinPortConfigStorageType             StorageType,
    latinSendString                        OctetString,
    latinPortLastChars                     OctetString,
    latinPortLastCharReceivedTime          OctetString,
    latinPortLastCharReceivedTimeStamp     TimeStamp,
    latinPortNoCharsTrapPeriod             Integer32,
    latinPortModemStatusSummary            BITS,
    latinPortModemStatusMask               BITS,
    latinPortModemStatusLastChangeSignals      BITS,
    latinPortModemStatusLastChangeTime         OctetString,
    latinPortModemStatusLastChangeTimeStamp    TimeStamp,
    latinPortModemStatusChangeTrapEnable   INTEGER,
    latinPortCharacterTranslationTable     OctetString
}

latinPortIndex OBJECT-TYPE
    SYNTAX     Integer32 
    MAX-ACCESS not-accessible
    STATUS     current
    DESCRIPTION "Provides a unique numerical index for rows in this table."
::= { latinPortConfigEntry 1 }

latinPortDeviceDescr OBJECT-TYPE
    SYNTAX     DisplayString 
    MAX-ACCESS read-write
    STATUS     current
    DESCRIPTION "Lets you name or specify the type of the character stream
                 device; e.g., telephone switch, thermostat, flood sensor, etc.  
                 The LATIN agent does not restrict the value of the 
                 latinPortDeviceDescr display string.

                 The latinPortDeviceDescr should provide useful information 
                 to network operators.  SNMP management applications may use 
                 this information to determine how to manage the character 
                 stream device."
::= { latinPortConfigEntry 2 }

latinPortDeviceComment OBJECT-TYPE
    SYNTAX     DisplayString 
    MAX-ACCESS read-write
    STATUS     current
    DESCRIPTION "Lets you specify additional information about the character
                 stream device.

                 The LATIN agent does not restrict the value of the 
                 latinPortDeviceComment display string.

                 The latinPortDeviceComment should provide useful information
                 to network operators, such as device sub model, equipment
                 rack location in a machine room, etc."
::= { latinPortConfigEntry 3 }

latinTrapPeriod OBJECT-TYPE
    SYNTAX     Integer32 
    MAX-ACCESS read-write
    STATUS     current
    DESCRIPTION "When a LATIN agent receives new data records from a character
                 stream device, it can alert an SNMP management application. 
                 To do this, the LATIN agent sends a latinMoreDataTrap to the
                 SNMP management application.

                 The latinTrapPeriod specifies the number of seconds between 
                 the LATIN more data available traps.

                 The LATIN agent does not restrict the value of the 
                 latinTrapPeriod Integer32.  Setting latinTrapPeriod to zero
                 disables latinMoreDataTraps."
::= { latinPortConfigEntry 4 }

latinPortConfigStorageType OBJECT-TYPE
    SYNTAX     StorageType 
    MAX-ACCESS read-write
    STATUS     current
    DESCRIPTION "Does nothing."
::= { latinPortConfigEntry 5 }

latinSendString OBJECT-TYPE
    SYNTAX     OCTET STRING
    MAX-ACCESS read-create
    STATUS     current
    DESCRIPTION "If you set the latinSendString, the LATIN agent sends it to
                 the character stream device.  This lets your SNMP management 
                 application send ad-hoc commands to the character stream
                 device. 

                 The LATIN agent does not restrict the value of the 
                 latinSendString octet string."
::= { latinPortConfigEntry 6 }

latinPortLastChars OBJECT-TYPE
    SYNTAX      OCTET STRING
    MAX-ACCESS  read-only
    STATUS      current
    DESCRIPTION "Contains the most recently received characters from the 
                 incoming character stream, regardless of whether the 
                 characters have been processed by the recordizer or not.
                 Conceptually, this object samples the character stream 
                 before any character translation occurs and before the 
                 recordizer. The actual number of characters returned will 
                 be implementation dependent."
::= { latinPortConfigEntry 7 }

latinPortLastCharReceivedTime OBJECT-TYPE
    SYNTAX      OCTET STRING
    MAX-ACCESS  read-only
    STATUS      current
    DESCRIPTION "Specifies the most recent time a character arrived from 
                 the character stream.  The LATIN agent records this time
                 stamp in the format provided by the operating system
                 under which the LATIN agent runs.  On some systems, this
                 object may be the empty string.  On open systems, this
                 object may contain time stamps in a format similar to that
                 provided by the date(1) command."
::= { latinPortConfigEntry 8 }

latinPortLastCharReceivedTimeStamp OBJECT-TYPE
    SYNTAX      TimeStamp
    MAX-ACCESS  read-only
    STATUS      current
    DESCRIPTION "Specifies the most recent time a character arrived from 
                 the character stream.  The LATIN agent records this time
                 stamp in the sysUpTime format."
::= { latinPortConfigEntry 9 }

latinPortNoCharsTrapPeriod OBJECT-TYPE
    SYNTAX      Integer32
    UNITS       "Seconds"
    MAX-ACCESS  read-create
    STATUS      current
    DESCRIPTION "Specifies a time period to wait for additional characters
                 from the character stream.  If the agent does not receive
                 additional characters from the character stream in this time
                 period, then the agent will send a latinPortNoCharsTrap.
                 Setting this object to 0 disables the sending of the
                 latinPortNoCharsTraps."
    DEFVAL      { 0 }
::= { latinPortConfigEntry 10 }

latinPortModemStatusSummary OBJECT-TYPE
    SYNTAX      BITS {
                  clearToSend(0),
                  dataSetReady(1),
                  ringIndicator(2),
                  dataCarrierDetect(3)
                }
    MAX-ACCESS  read-only
    STATUS      current
    DESCRIPTION "Shows the current status of modem status input signals.  The 
                 individual bits in this object show the status of individual 
                 modem input signals.  If the agent cannot get the status of 
                 these modem input signals from the hardware platform, the 
                 corresponding bit positions will be set to zero."
::= { latinPortConfigEntry 11 }

latinPortModemStatusMask OBJECT-TYPE
    SYNTAX      BITS {
                  clearToSend(0),
                  dataSetReady(1),
                  ringIndicator(2),
                  dataCarrierDetect(3)
                }
    MAX-ACCESS  read-create
    STATUS      current
    DESCRIPTION "Defines which of the modem status input signals the LATIN
                 agent will monitor for changes."
::= { latinPortConfigEntry 12 }

latinPortModemStatusLastChangeSignals OBJECT-TYPE
    SYNTAX      BITS {
                  clearToSend(0),
                  dataSetReady(1),
                  ringIndicator(2),
                  dataCarrierDetect(3)
                }
    MAX-ACCESS  read-only
    STATUS      current
    DESCRIPTION "Shows which modem status input signal(s) changed most
                 recently."
::= { latinPortConfigEntry 13 }

latinPortModemStatusLastChangeTime OBJECT-TYPE
    SYNTAX      OCTET STRING
    MAX-ACCESS  read-only
    STATUS      current
    DESCRIPTION "Specifies the most recent time the modem status input 
                 signals changed.  The LATIN agent records this time stamp
                 in the format provided by the operating system under which 
                 the LATIN agent runs.   On some systems, this object may be 
                 the empty string.  On open systems, this object may contain 
                 time stamps in a format similar to that provided by the 
                 date(1) command."
::= { latinPortConfigEntry 14 }

latinPortModemStatusLastChangeTimeStamp OBJECT-TYPE
    SYNTAX      TimeStamp
    MAX-ACCESS  read-only
    STATUS      current
    DESCRIPTION "Specifies the most recent time the modem status input 
                 signals changed.  The LATIN agent records this time stamp 
                 in the sysUpTime format."
::= { latinPortConfigEntry 15 }

latinPortModemStatusChangeTrapEnable OBJECT-TYPE
    SYNTAX      INTEGER{
                disable(1),
                enable(2)
                }
    MAX-ACCESS  read-create
    STATUS      current
    DESCRIPTION "Enables the sending of latinPortModemStatusChangeTraps.
                 If this MIB object is set to enable, then the LATIN agent
                 will send a trap when the modem status input signals change."
    DEFVAL      { disable }
::= { latinPortConfigEntry 16 }

latinPortCharacterTranslationTable OBJECT-TYPE
    SYNTAX      OCTET STRING (SIZE(0|1|256))
    MAX-ACCESS  read-create
    STATUS      current
    DESCRIPTION "Specifies the character translation table for characters
                 coming from the port. 

                 If this MIB object is set to an octet string of length zero, 
                 character translation is disabled.  If this MIB object is 
                 set to a single octet 0x00, then the LATIN agent will set 
                 the tranlation table to its default value.  With a separate
                 SNMP get request, the management station then can retrieve
                 this default translation table for manipulation.  If this
                 MIB object is set to an octet string of length 256, then 
                 this MIB object lets the user specify the character trans-
                 lation table.

                 The translate-from character is specified by it's position
                 in the octet string.  The translate-to character is spec-
                 ified by the value of that octet.

                 For example, to translate incoming null characters (with a 
                 byte value of 0x00) to space characters (with an ASCII byte 
                 value of 0x20), the 1st octet of this MIB object must be 
                 set to 0x20.  

                 As a second example, to translate escape characters (with an 
                 ASCII byte value of 0x1B) to tab characters (with an ASCII 
                 byte value of 0x09), the 28th octet (0x1B is 27 in decimal, 
                 plus 1 because the octet numbering of this MIB object starts 
                 at 1 instead of 0) must be set to a 0x09.

                 The default translation table is:

                     00 01 02 03 04 05 06 07  08 09 0a 0b 0c 0d 0e 0f
                     10 11 12 13 14 15 16 17  18 19 1a 1b 1c 1d 1e 1f
                     20 21 22 23 24 25 26 27  28 29 2a 2b 2c 2d 2e 2f
                     30 31 32 33 34 35 36 37  38 39 3a 3b 3c 3d 3e 3f
                     40 41 42 43 44 45 46 47  48 49 4a 4b 4c 4d 4e 4f
                     50 51 52 53 54 55 56 57  58 59 5a 5b 5c 5d 5e 5f
                     60 61 62 63 64 65 66 67  68 69 6a 6b 6c 6d 6e 6f
                     70 71 72 73 74 75 76 77  78 79 7a 7b 7c 7d 7e 7f
                     80 81 82 83 84 85 86 87  88 89 8a 8b 8c 8d 8e 8f
                     90 91 92 93 94 95 96 97  98 99 9a 9b 9c 9d 9e 9f
                     a0 a1 a2 a3 a4 a5 a6 a7  a8 a9 aa ab ac ad ae af
                     b0 b1 b2 b3 b4 b5 b6 b7  b8 b9 ba bb bc bd be bf
                     c0 c1 c2 c3 c4 c5 c6 c7  c8 c9 ca cb cc cd ce cf
                     d0 d1 d2 d3 d4 d5 d6 d7  d8 d9 da db dc dd de df
                     e0 e1 e2 e3 e4 e5 e6 e7  e8 e9 ea eb ec ed ee ef
                     f0 f1 f2 f3 f4 f5 f6 f7  f8 f9 fa fb fc fd fe ef"
::= { latinPortConfigEntry 17 }


--
--
-- The LATIN direct send table.
--
--

latinDirectSendTable OBJECT-TYPE
    SYNTAX     SEQUENCE OF LatinDirectSendEntry
    MAX-ACCESS not-accessible
    STATUS     current
    DESCRIPTION "Configures the LATIN agent to automatically poll the
                 character stream device at regular intervals.  This table
                 configures multiple character streams, multiple poll strings, 
                 and multiple time intervals."
::= { latinGeneralInfo 4 }

latinDirectSendEntry OBJECT-TYPE
    SYNTAX     LatinDirectSendEntry
    MAX-ACCESS not-accessible
    STATUS     current
    DESCRIPTION "Configures a single command and time interval for polling
                 a serial port device."
    INDEX { latinPortIndex, latinDirectSendIndex }
::= { latinDirectSendTable 1 }

LatinDirectSendEntry ::= SEQUENCE {
    latinDirectSendIndex Integer32,
    latinDirectSendString OctetString,
    latinDirectSendTimer Integer32,
    latinDirectSendEventCategory Integer32,
    latinDirectSendStorageType StorageType,
    latinDirectSendStatus RowStatus
}

latinDirectSendIndex OBJECT-TYPE
    SYNTAX     Integer32 
    MAX-ACCESS not-accessible
    STATUS     current
    DESCRIPTION "Provides a unique numerical index for rows in this table."
::= { latinDirectSendEntry 1 }

latinDirectSendString OBJECT-TYPE
    SYNTAX     OCTET STRING
    MAX-ACCESS read-create
    STATUS     current
    DESCRIPTION "Specifies the command string the LATIN agent should use to 
                 poll the character stream device. 

                 The LATIN agent does not restrict the value of the 
                 latinDirectSendString octet string."
::= { latinDirectSendEntry 2 }

latinDirectSendTimer OBJECT-TYPE
    SYNTAX     Integer32 
    MAX-ACCESS read-create
    STATUS     current
    DESCRIPTION "Specifies the time interval, in seconds, at which the LATIN
                 agent transmits the corresponding poll command string to the 
                 character stream device.  

                 The LATIN agent does not restrict the value of the 
                 latinDirectSendTimer Integer32."
::= { latinDirectSendEntry 3 }

latinDirectSendEventCategory OBJECT-TYPE
    SYNTAX     Integer32 
    MAX-ACCESS read-create
    STATUS     current
    DESCRIPTION " "
::= { latinDirectSendEntry 4 }

latinDirectSendStorageType OBJECT-TYPE
    SYNTAX     StorageType 
    MAX-ACCESS read-create
    STATUS     current
    DESCRIPTION "Does nothing."
::= { latinDirectSendEntry 5 }

latinDirectSendStatus OBJECT-TYPE
    SYNTAX     RowStatus 
    MAX-ACCESS read-create
    STATUS     current
    DESCRIPTION "This is the row status for this table."
::= { latinDirectSendEntry 6 }

--
--
-- The latinRecord Group
--
--

latinRecord OBJECT IDENTIFIER ::= { latin 2 }
 
latinRecordConfigTable OBJECT-TYPE
    SYNTAX     SEQUENCE OF LatinRecordConfigEntry
    MAX-ACCESS not-accessible
    STATUS     current
    DESCRIPTION "The LATIN agent receives incoming character streams. It 
                 splits the incoming character streams into data records.

                 The latinRecordConfigTable specifies how the LATIN agent
                 splits the character streams into data records."
::= { latinRecord 1 }

latinRecordConfigEntry OBJECT-TYPE
    SYNTAX     LatinRecordConfigEntry
    MAX-ACCESS not-accessible
    STATUS     current
    DESCRIPTION "Specifies how the LATIN agent splits a single character 
                 stream into data records."
    INDEX { latinPortIndex }
::= { latinRecordConfigTable 1 }

LatinRecordConfigEntry ::= SEQUENCE {
    latinRecordSeparator OCTET STRING,
    latinRecordSeparatorType INTEGER,
    latinRecordSeparatorInclusion INTEGER,
    latinRecordConfigStorageType StorageType
}

latinRecordSeparator OBJECT-TYPE
    SYNTAX     OCTET STRING
    MAX-ACCESS read-write
    STATUS     current
    DESCRIPTION "Specifies an octet string that identifies a boundary between
                 data records in an incoming character stream.

                 The LATIN agent does not restrict the value of the 
                 latinRecordSeparator octet string.

                 For example, if the incoming character stream uses an ASCII 
                 carriage-return/line-feed sequence as the record boundary, 
                 then the latinRecordSeparator should be 0D 0A, the hexadecimal
                 values for the carriage-return/line feed characters."
::= { latinRecordConfigEntry 1 }

latinRecordSeparatorType OBJECT-TYPE
    SYNTAX     INTEGER{
                   exactMatchAtStart(1),
                   exactMatchAtEnd(2),
                   regularExpressionAtStart(3),
                   regularExpressionAtEnd(4)
                   } 
    MAX-ACCESS read-write
    STATUS     current
    DESCRIPTION "Specifies where the latinRecordSeparator will appear in the
                 data line. 

                 exactMatchAtStart(1)        - Split the incoming character 
                      stream when the octets in latinRecordSeparator are
                      received.  Put the octets in latinRecordSeparator at
                      the start of the next record.

                 exactMatchAtEnd(2)          - Split the incoming character 
                      stream when the octets in latinRecordSeparator are
                      received.  Put the octets in latinRecordSeparator at
                      the end of the previous record.

                 regularExpressionAtStart(3) - Unimplemented.

                 regularExpressionAtEnd(4)   - Unimplemented."
::= { latinRecordConfigEntry 2 }

latinRecordSeparatorInclusion OBJECT-TYPE
    SYNTAX     INTEGER{
                   excludeFromRecord(1),
                   includeInRecord(2)
                   }
    MAX-ACCESS read-write
    STATUS     current
    DESCRIPTION "Specifies whether the LATIN agent will keep or delete 
                 latinRecordSeparator from the incoming data records.

                 excludeFromRecord(1) -  Delete latinRecordSeparator from the 
                                         incoming data record.

                 includeInRecord(2) -    Keep latinRecordSeparator in the 
                                         incoming data record."
::= { latinRecordConfigEntry 3 }

latinRecordConfigStorageType OBJECT-TYPE
    SYNTAX     StorageType 
    MAX-ACCESS read-write
    STATUS     current
    DESCRIPTION "Does nothing."
::= { latinRecordConfigEntry 4 }

--
--
-- The LATIN record history control table.
--
--

latinRecordHistoryControlTable OBJECT-TYPE
    SYNTAX     SEQUENCE OF LatinRecordHistoryControlEntry
    MAX-ACCESS not-accessible
    STATUS     current
    DESCRIPTION "After splitting the incoming character stream into data
                 records, the LATIN agent temporarily stores the data records
                 in a table.  The LATIN agent deletes the oldest data records
                 to provide storage for the newest records. 

                 The latinRecordHistoryTable temporarily stores the incoming
                 data records.  

                 This table defines the parameters for the 
                 latinRecordHistoryTable for all data streams."
::= { latinRecord 2 }

latinRecordHistoryControlEntry OBJECT-TYPE
    SYNTAX     LatinRecordHistoryControlEntry
    MAX-ACCESS not-accessible
    STATUS     current
    DESCRIPTION "Defines the parameters for the latinRecordHistoryTables for 
                 a single character stream. "
    INDEX { latinPortIndex }
::= { latinRecordHistoryControlTable 1 }

LatinRecordHistoryControlEntry ::= SEQUENCE {
    latinRecordBucketsRequested Integer32,
    latinRecordTimeOutTime Integer32,
    latinRecordStorageType StorageType
}

latinRecordBucketsRequested OBJECT-TYPE
    SYNTAX     Integer32 
    MAX-ACCESS read-write
    STATUS     current
    DESCRIPTION "Specifies the desired number of data records temporarily 
                 stored in the latinRecordHistoryTable.

                 The LATIN agent does not artificially restrict the values of 
                 the latinRecordHistoryBucketsRequested Integer32.  The 
                 agent might have a practical limit, such as the memory size."
::= { latinRecordHistoryControlEntry 1 }

latinRecordTimeOutTime OBJECT-TYPE
    SYNTAX     Integer32 
    MAX-ACCESS read-write
    STATUS     current
    DESCRIPTION "Specifies a minimum time interval, in seconds, that the LATIN 
                 agent retains a data record in the latinRecordHistoryTable.

                 The LATIN agent does not artificially restrict the values of 
                 the latinRecordTimeOut Integer32.  If latinRecordTimeOutTime 
                 is set to zero, the LATIN agent does not expire records based 
                 on age."
::= { latinRecordHistoryControlEntry 2 }

latinRecordStorageType OBJECT-TYPE
    SYNTAX     StorageType 
    MAX-ACCESS read-write
    STATUS     current
    DESCRIPTION "Does nothing."
::= { latinRecordHistoryControlEntry 3 }

--
--
-- The LATIN record history table.
--
--

latinRecordHistoryTable OBJECT-TYPE
    SYNTAX     SEQUENCE OF LatinRecordHistoryEntry
    MAX-ACCESS not-accessible
    STATUS     current
    DESCRIPTION "After splitting the incoming character stream into data
                 records, the LATIN agent temporarily stores the data records
                 in a table.  The LATIN agent deletes the oldest data records
                 to provide storage for the newest records. 

                 This table temporarily stores the incoming data records."
::= { latinRecord 3 }

latinRecordHistoryEntry OBJECT-TYPE
    SYNTAX     LatinRecordHistoryEntry
    MAX-ACCESS not-accessible
    STATUS     current
    DESCRIPTION "Stores a single incoming data record and related information."
    INDEX { latinPortIndex, latinRecordHistoryIndex }
::= { latinRecordHistoryTable 1 }

LatinRecordHistoryEntry ::= SEQUENCE {
    latinRecordHistoryIndex Integer32,
    latinRecordHistoryData OctetString,
    latinRecordHistoryTime OctetString,
    latinRecordHistoryTimeStamp TimeStamp,
    latinRecordHistoryState INTEGER
}

latinRecordHistoryIndex OBJECT-TYPE
    SYNTAX     Integer32 
    MAX-ACCESS not-accessible
    STATUS     current
    DESCRIPTION "Provides a unique numerical index for rows in this table."
::= { latinRecordHistoryEntry 1 }

latinRecordHistoryData OBJECT-TYPE
    SYNTAX     OCTET STRING
    MAX-ACCESS read-only
    STATUS     current
    DESCRIPTION "Contains the incoming data record."
::= { latinRecordHistoryEntry 2 }

latinRecordHistoryTime OBJECT-TYPE
    SYNTAX     OCTET STRING
    MAX-ACCESS read-only
    STATUS     current
    DESCRIPTION "Specifies the time the incoming record arrived.  The LATIN 
                 agent records this time stamp in the format provided by the 
                 operating system under which the LATIN agent runs."
::= { latinRecordHistoryEntry 3 }

latinRecordHistoryTimeStamp OBJECT-TYPE
    SYNTAX     TimeStamp 
    MAX-ACCESS read-only
    STATUS     current
    DESCRIPTION "Specifies the time the incoming record arrived.  The LATIN 
                 agent records this time stamp in sysUpTime format."
::= { latinRecordHistoryEntry 4 }

latinRecordHistoryState OBJECT-TYPE
    SYNTAX     INTEGER{
                   notProcessed(1),
                   processedAndMatched(2),
                   processedAndNotMatched(3)
                   } 
    MAX-ACCESS read-only
    STATUS     current
    DESCRIPTION " "
::= { latinRecordHistoryEntry 5 }

--
--
-- The latinFilter Group
--
--

latinFilter OBJECT IDENTIFIER ::= { latin 3 }

--
--
-- The LATIN filter row available table.
--
--
 
latinFilterAvailableRowTable OBJECT-TYPE
    SYNTAX     SEQUENCE OF LatinFilterAvailableRowEntry
    MAX-ACCESS not-accessible
    STATUS     current
    DESCRIPTION "For all character streams, this table provides the index of 
                 an available row in the latinFilterTable.  The character 
                 stream number provides the index for this table."
::= { latinFilter 1 }

latinFilterAvailableRowEntry OBJECT-TYPE
    SYNTAX     LatinFilterAvailableRowEntry
    MAX-ACCESS not-accessible
    STATUS     current
    DESCRIPTION "For a single character stream, this provides the index of
                 an available row in the latinFilterTable. "
    INDEX { latinPortIndex }
::= { latinFilterAvailableRowTable 1 }

LatinFilterAvailableRowEntry ::= SEQUENCE {
    latinFilterAvailableRow Integer32
}

latinFilterAvailableRow OBJECT-TYPE
    SYNTAX     Integer32 
    MAX-ACCESS read-only
    STATUS     current
    DESCRIPTION "SNMP management applications can retreive this object to get
                 the index of an available row in the latinFilterTable."
::= { latinFilterAvailableRowEntry 1 }

--
--
-- The latinFilterTable.
--
--

latinFilterTable OBJECT-TYPE
    SYNTAX     SEQUENCE OF LatinFilterEntry
    MAX-ACCESS not-accessible
    STATUS     current
    DESCRIPTION "After receiving an incoming data record, the LATIN agent
                 compares the incoming data record to each entry in a table 
                 of regular expressions (character strings.)  If the LATIN 
                 agent finds the regular expression in the incoming data
                 record, it assigns a message/event category number to the
                 data record.

                 This table specifies the regular expressions.  If the LATIN 
                 agent finds the regular expression in the incoming data 
                 record, it assigns latinEventFilterCategory to the the 
                 incoming data record."
::= { latinFilter 2 }

latinFilterEntry OBJECT-TYPE
    SYNTAX     LatinFilterEntry
    MAX-ACCESS not-accessible
    STATUS     current
    DESCRIPTION "Contains a single regular expression and related information."
    INDEX { latinPortIndex, latinFilterIndex }
::= { latinFilterTable 1 }

LatinFilterEntry ::= SEQUENCE {
    latinFilterIndex     Integer32,
    latinFilterMatchString DisplayString,
    latinFilterMatchStringType INTEGER,
    latinFilterDescr     DisplayString,
    latinFilterStartPosition Integer32,
    latinFilterStopPosition Integer32,
    latinFilterMatches   Integer32,
    latinFilterPriority  Integer32,
    latinFilterContinueMatching Integer32,
    latinFilterConfigOwner DisplayString,
    latinFilterEventCategory Integer32,
    latinFilterStorageType StorageType,
    latinFilterStatus    RowStatus
}

latinFilterIndex OBJECT-TYPE
    SYNTAX     Integer32 
    MAX-ACCESS not-accessible
    STATUS     current
    DESCRIPTION "Provides a unique numerical index for rows in this table."
::= { latinFilterEntry 1 }

latinFilterMatchString OBJECT-TYPE
    SYNTAX     DisplayString 
    MAX-ACCESS read-create
    STATUS     current
    DESCRIPTION "Contains the regular expression string.

                 The LATIN agent compares will search each incoming data 
                 record looking for this match string.

                 The LATIN agent does not restrict the value of the 
                 latinFilterMatchString display string."
::= { latinFilterEntry 2 }

latinFilterMatchStringType OBJECT-TYPE
    SYNTAX     INTEGER{
                   exactMatch(1),
                   regularExpression(2)
                   } 
    MAX-ACCESS read-create
    STATUS     current
    DESCRIPTION "Specifies: 

                 exactMatch(1)        - the LATIN agent must exactly match
                                        latinFilterMatchString in the incoming 
                                        data record.

                 regularExpression(2) - the LATIN agent interprets
                                        latinFilterMatchString as a regular 
                                        expression template."
::= { latinFilterEntry 3 }

latinFilterDescr OBJECT-TYPE
    SYNTAX     DisplayString 
    MAX-ACCESS read-create
    STATUS     current
    DESCRIPTION "Lets you document the filter.  The LATIN agent does not 
                 restrict the value of the latinFilterDescr display string.

                 You should document the significance of the regular expression.
                 Examples:  Temperatures over 30 degrees C, Outgoing calls
                 made to 1-900 telephone numbers, etc."
::= { latinFilterEntry 4 }

latinFilterStartPosition OBJECT-TYPE
    SYNTAX     Integer32 
    MAX-ACCESS read-create
    STATUS     current
    DESCRIPTION "The LATIN agent starts searching for the regular expression
                 at character position  latinFilterStartPosition  in the 
                 incoming data record.

                 If latinFilterStartPosition is set to zero or less than zero,
                 then the value of latinFilterStartPosition is ignored.
                 Otherwise, the LATIN agent will attempt to match the portion
                 of a received message beginning at the position specified
                 by latinFilterStartPosition.

                 If latinFilterStartPosition is set to be greater than the
                 last position in the data record, the regular expression
                 is not matched."
::= { latinFilterEntry 5 }

latinFilterStopPosition OBJECT-TYPE
    SYNTAX     Integer32 
    MAX-ACCESS read-create
    STATUS     current
    DESCRIPTION "The LATIN agent stops searching for the regular expression
                 at character position  latinFilterStartPosition  in the 
                 incoming data record.

                 If latinFilterStopPosition is set to zero or less than zero,
                 then the value of latinFilterStopPosition is ignored.
                 Otherwise, the LATIN agent will attempt to match the
                 portion of a received message ending at the position
                 specified by latinFilterStopPosition."
::= { latinFilterEntry 6 }

latinFilterMatches OBJECT-TYPE
    SYNTAX     Integer32 
    MAX-ACCESS read-create
    STATUS     current
    DESCRIPTION "Counts the number of times this regular expression has
                 been found in the incoming data records."
::= { latinFilterEntry 7 }

latinFilterPriority OBJECT-TYPE
    SYNTAX     Integer32 
    MAX-ACCESS read-create
    STATUS     current
    DESCRIPTION "Does nothing."
::= { latinFilterEntry 8 }

latinFilterContinueMatching OBJECT-TYPE
    SYNTAX     Integer32 
    MAX-ACCESS read-create
    STATUS     current
    DESCRIPTION "Does nothing."
::= { latinFilterEntry 9 }

latinFilterConfigOwner OBJECT-TYPE
    SYNTAX     DisplayString 
    MAX-ACCESS read-create
    STATUS     current
    DESCRIPTION "Lets you specify who created this filter.

                 The LATIN agent does not artificially restrict the values of
                 the latinFilterConfigOwner display string."
::= { latinFilterEntry 10 }

latinFilterEventCategory OBJECT-TYPE
    SYNTAX     Integer32 
    MAX-ACCESS read-create
    STATUS     current
    DESCRIPTION "If the LATIN agent finds the corresponding regular expression
                 in the incoming data record, then it assigns this event
                 category to the incoming data record.  The event category 
                 identifies an action item in the latinEventTable to execute
                 for further processing of the matched record.
 
                 For example, if a regular expression match occurs, and the
                 latinFilterEventCategory  is the number 3, then row 3 in
                 the latinEventTable specifies the action item.

                 The LATIN agent does not artificially restrict the values of
                 the latinFilterEventCategory Integer32, but this object must
                 identify a valid, already existing, row in the 
                 latinEventTable."
::= { latinFilterEntry 11 }

latinFilterStorageType OBJECT-TYPE
    SYNTAX     StorageType 
    MAX-ACCESS read-create
    STATUS     current
    DESCRIPTION "Does nothing."
::= { latinFilterEntry 12 }

latinFilterStatus OBJECT-TYPE
    SYNTAX     RowStatus 
    MAX-ACCESS read-create
    STATUS     current
    DESCRIPTION "This is the row status for this table."
::= { latinFilterEntry 13 }

--
--
-- The latinFilterHistoryControlTable.
--
--

latinFilterHistoryControlTable OBJECT-TYPE
    SYNTAX     SEQUENCE OF LatinFilterHistoryControlEntry
    MAX-ACCESS not-accessible
    STATUS     current
    DESCRIPTION "If an incoming data record matches a regular expression, the 
                 LATIN agent temporarily stores the matched data record in the 
                 latinFilterHistory table.  This lets you see the data records 
                 that have matched a regular expression.

                 This table lets you specify how many/how long incoming data
                 records are kept in the latinFilterHistoryTable for all
                 character data streams."
::= { latinFilter 3 }

latinFilterHistoryControlEntry OBJECT-TYPE
    SYNTAX     LatinFilterHistoryControlEntry
    MAX-ACCESS not-accessible
    STATUS     current
    DESCRIPTION "This lets you specify how many/how long incoming data records 
                 are kept in the latinFilterHistoryTable for a single character
                 data stream."
    INDEX { latinPortIndex }
::= { latinFilterHistoryControlTable 1 }

LatinFilterHistoryControlEntry ::= SEQUENCE {
    latinFilterHistoryControlBucketsRequested Integer32,
    latinFilterHistoryControlTimeOutTime Integer32,
    latinFilterHistoryControlStorageType StorageType
}

latinFilterHistoryControlBucketsRequested OBJECT-TYPE
    SYNTAX     Integer32 
    MAX-ACCESS read-write
    STATUS     current
    DESCRIPTION "Specifies the desired number of data records temporarily 
                 stored in the latinFilterHistoryTable.

                 The LATIN agent does not artificially restrict the values of 
                 the latinFilterHistoryControlBucketsRequested Integer32.  The 
                 agent might have a practical limit, such as the memory size."
::= { latinFilterHistoryControlEntry 1 }

latinFilterHistoryControlTimeOutTime OBJECT-TYPE
    SYNTAX     Integer32 
    MAX-ACCESS read-write
    STATUS     current
    DESCRIPTION "Specifies a minimum time interval, in seconds, that the LATIN 
                 agent retains a data record in the latinFilterHistoryTable.

                 The LATIN agent does not artificially restrict the values of 
                 the latinFilterHistoryControlTimeout Integer32.  If this 
                 object is set to zero, the LATIN agent does not expire the
                 records based on age."
::= { latinFilterHistoryControlEntry 2 }

latinFilterHistoryControlStorageType OBJECT-TYPE
    SYNTAX     StorageType 
    MAX-ACCESS read-write
    STATUS     current
    DESCRIPTION "Does nothing."
::= { latinFilterHistoryControlEntry 3 }

--
--
-- The latinFilterHistoryTable.
--
--

latinFilterHistoryTable OBJECT-TYPE
    SYNTAX     SEQUENCE OF LatinFilterHistoryEntry
    MAX-ACCESS not-accessible
    STATUS     current
    DESCRIPTION "If an incoming data record matches a regular expression, the 
                 LATIN agent temporarily stores the data record in the 
                 latinFilterHistory table.  This lets you see the data records 
                 that have matched one of the regular expressions."
::= { latinFilter 4 }

latinFilterHistoryEntry OBJECT-TYPE
    SYNTAX     LatinFilterHistoryEntry
    MAX-ACCESS not-accessible
    STATUS     current
    DESCRIPTION "Contains one of the matched data records and its associated
                 information."
    INDEX { latinPortIndex, latinFilterHistoryIndex }
::= { latinFilterHistoryTable 1 }

LatinFilterHistoryEntry ::= SEQUENCE {
    latinFilterHistoryIndex Integer32,
    latinFilterHistoryData OctetString,
    latinFilterHistoryTime OctetString,
    latinFilterHistoryTimeStamp TimeStamp,
    latinFilterHistoryFilterIndex Integer32
}

latinFilterHistoryIndex OBJECT-TYPE
    SYNTAX     Integer32 
    MAX-ACCESS not-accessible
    STATUS     current
    DESCRIPTION "Provides a unique numerical index for rows in this table."
::= { latinFilterHistoryEntry 1 }

latinFilterHistoryData OBJECT-TYPE
    SYNTAX     OCTET STRING
    MAX-ACCESS read-only
    STATUS     current
    DESCRIPTION "Contains the matched data record."
::= { latinFilterHistoryEntry 2 }

latinFilterHistoryTime OBJECT-TYPE
    SYNTAX     OCTET STRING
    MAX-ACCESS read-only
    STATUS     current
    DESCRIPTION "Specifies the time the incoming record arrived.  The LATIN 
                 agent records this time stamp in the format provided by the
                 operating system under which the LATIN agent runs."
::= { latinFilterHistoryEntry 3 }

latinFilterHistoryTimeStamp OBJECT-TYPE
    SYNTAX     TimeStamp 
    MAX-ACCESS read-only
    STATUS     current
    DESCRIPTION "Specifies the time the incoming record arrived.  The LATIN 
                 agent records this time stamp in sysUpTime format."
::= { latinFilterHistoryEntry 4 }

latinFilterHistoryFilterIndex OBJECT-TYPE
    SYNTAX     Integer32 
    MAX-ACCESS read-only
    STATUS     current
    DESCRIPTION "Identifies which regular expression this data record matched.
                 This object stores the latinFilterTable index of the 
                 corresponding regular expression."
::= { latinFilterHistoryEntry 5 }

--
--
-- The latinEvent Group
--
--

latinEvent OBJECT IDENTIFIER ::= { latin 4 }

--
--
-- The latinEventAvailableRowTable.
--
--
 
latinEventAvailableRowTable OBJECT-TYPE
    SYNTAX     SEQUENCE OF LatinEventAvailableRowEntry
    MAX-ACCESS not-accessible
    STATUS     current
    DESCRIPTION "For all character streams, this table provides the index of
                 an available row in the latinEventTable.  The character
                 stream number provides the index for this table."
::= { latinEvent 1 }

latinEventAvailableRowEntry OBJECT-TYPE
    SYNTAX     LatinEventAvailableRowEntry
    MAX-ACCESS not-accessible
    STATUS     current
    DESCRIPTION "For a single character stream, this provides the index of
                 an available row in the latinEventTable. "
    INDEX { latinPortIndex }
::= { latinEventAvailableRowTable 1 }

LatinEventAvailableRowEntry ::= SEQUENCE {
    latinEventAvailableRow Integer32
}

latinEventAvailableRow OBJECT-TYPE
    SYNTAX     Integer32 
    MAX-ACCESS read-only
    STATUS     current
    DESCRIPTION "SNMP management applications can retreive this object to get
                 the index of an available row in the latinEventTable."
::= { latinEventAvailableRowEntry 1 }

--
--
-- The latinEventTable.
--
--

latinEventTable OBJECT-TYPE
    SYNTAX     SEQUENCE OF LatinEventEntry
    MAX-ACCESS not-accessible
    STATUS     current
    DESCRIPTION "For all ports, this table specifies all events (the actions) 
                 the LATIN agent should run when a data record matches a 
                 regular expression."
::= { latinEvent 2 }

latinEventEntry OBJECT-TYPE
    SYNTAX     LatinEventEntry
    MAX-ACCESS not-accessible
    STATUS     current
    DESCRIPTION "Specifies a single event."
    INDEX { latinPortIndex, latinEventIndex }
::= { latinEventTable 1 }

LatinEventEntry ::= SEQUENCE {
    latinEventIndex      Integer32,
    latinEventCategoryDescr DisplayString,
    latinEventCategoryOwner DisplayString,
    latinEventType       Integer32,
    latinEventLogTableBucketsRequested Integer32,
    latinEventLogTableTimeOutTime Integer32,
    latinEventLogFileName DisplayString,
    latinEventTrapChain  INTEGER,
    latinEventAutoResponse OctetString,
    latinEventAutoResponsePort Integer32,
    latinEventScriptName OctetString,
    latinEventDependsOn  Integer32,
    latinEventActivated  INTEGER,
    latinEventLifetimeType INTEGER,
    latinEventLifetime   Integer32,
    latinEventStorageType StorageType,
    latinEventStatus     RowStatus,
    latinEventSoftTrap OctetString,
    latinEventSoftTrapInstances OctetString
}

latinEventIndex OBJECT-TYPE
    SYNTAX     Integer32 
    MAX-ACCESS not-accessible
    STATUS     current
    DESCRIPTION "Provides a unique numerical index for rows in this table."
::= { latinEventEntry 1 }

latinEventCategoryDescr OBJECT-TYPE
    SYNTAX     DisplayString 
    MAX-ACCESS read-create
    STATUS     current
    DESCRIPTION "Lets you describe the significance of the event. 

                 Example:  An unrecoverable communication error occurred. 

                 The LATIN agent does not restrict the value of the 
                 latinEventCategoryDescr display string."
::= { latinEventEntry 2 }

latinEventCategoryOwner OBJECT-TYPE
    SYNTAX     DisplayString 
    MAX-ACCESS read-create
    STATUS     current
    DESCRIPTION "Lets you specify who created this event."
::= { latinEventEntry 3 }

latinEventType OBJECT-TYPE
    SYNTAX     Integer32 
    MAX-ACCESS read-create
    STATUS     current
    DESCRIPTION "Specifies the action:

                  1 - save the record in an in-memory table.
                  2 - save the record in a file on non-volatile storage.
                  4 - send a trap.
                  8 - send a automatic response string out the serial port.
                 16 - run a script.

                 You can add these values together to produce combinations
                 of actions.  For example:

                 latinEventType 1 + latinEventType 4 = latinEventType 5

                 This would save the record to an in-memory table AND send 
                 a trap."
::= { latinEventEntry 4 }

latinEventLogTableBucketsRequested OBJECT-TYPE
    SYNTAX     Integer32 
    MAX-ACCESS read-create
    STATUS     current
    DESCRIPTION "As an event, a LATIN agent can log the incoming data records
                 to an in-memory table.  

                 This MIB object specifies the desired number of data records
                 stored in the latinLogDataTable for this event.

                 The LATIN agent does not restrict the value of this object,
                 but the agent may have practical limits, such as the memory 
                 size of the machine on which the agent runs."
::= { latinEventEntry 5 }

latinEventLogTableTimeOutTime OBJECT-TYPE
    SYNTAX     Integer32 
    MAX-ACCESS read-create
    STATUS     current
    DESCRIPTION "As an event, a LATIN agent can log the incoming data records
                 to an in-memory table.  

                 Specifies a minimum time interval, in seconds, that the LATIN
                 agent retains a data record in the latinLogDataTable.

                 The LATIN agent does not restrict the value of the 
                 latinEventLogTableTimeOutTime Integer32.  If it is set to
                 zero, the LATIN agent does not expire the records based on
                 age."
::= { latinEventEntry 6 }

latinEventLogFileName OBJECT-TYPE
    SYNTAX     DisplayString 
    MAX-ACCESS read-create
    STATUS     current
    DESCRIPTION "As an event, a LATIN agent can log the incoming data records
                 to a file on an external storage device.

                 The latinEventLogFileName object specifies the name of the
                 log file.

                 The LATIN agent does not restrict the value of the 
                 latinEventLogFileName display string."
::= { latinEventEntry 7 }

latinEventTrapChain OBJECT-TYPE
    SYNTAX     INTEGER{
                   none(1),
                   previous(2),
                   current(3),
                   both(4)
                   } 
    MAX-ACCESS read-create
    STATUS     current
    DESCRIPTION "Does nothing"
::= { latinEventEntry 8 }

latinEventAutoResponse OBJECT-TYPE
    SYNTAX     OCTET STRING
    MAX-ACCESS read-create
    STATUS     current
    DESCRIPTION "As an event, a LATIN agent can send an automatic response to
                 a serial-port device.  

                 The latinEventAutoResponse specifies the octet string to send 
                 as an automatic response.  

                 The LATIN agent does not restrict the value of the 
                 latinEventAutoResponse octet string."
::= { latinEventEntry 9 }

latinEventAutoResponsePort OBJECT-TYPE
    SYNTAX     Integer32 
    MAX-ACCESS read-create
    STATUS     current
    DESCRIPTION "As an event, a LATIN agent can send an automatic response to
                 a serial-port device.  

                 The latinEventAutoResponsePort specifies which serial port
                 the automatic response should be sent.  

                 The LATIN agent restricts the value of this object to values
                 between 0 and the highest numbered serial port.  A value
                 of 0 means send the response to the port the record came 
                 in on (latinPortIndex)."
::= { latinEventEntry 10 }

latinEventScriptName OBJECT-TYPE
    SYNTAX     OCTET STRING
    MAX-ACCESS read-create
    STATUS     current
    DESCRIPTION "As an event, a LATIN agent can run a script (program) to do
                 additional processing or actions.

                 The latinEventScriptName object specifies the script name 
                 the LATIN agent should run.  

                 The LATIN agent does not restrict the value of the 
                 latinEventScriptName octet string."
::= { latinEventEntry 11 }

latinEventDependsOn OBJECT-TYPE
    SYNTAX     Integer32 
    MAX-ACCESS read-create
    STATUS     current
    DESCRIPTION " "
::= { latinEventEntry 12 }

latinEventActivated OBJECT-TYPE
    SYNTAX     INTEGER{
                   activated(1),
                   deActivated(2),
                   deActivating(3)
                   } 
    MAX-ACCESS read-only
    STATUS     current
    DESCRIPTION " "
::= { latinEventEntry 13 }

latinEventLifetimeType OBJECT-TYPE
    SYNTAX     INTEGER{centiSeconds(1),numRecords(2)} 
    MAX-ACCESS read-create
    STATUS     current
    DESCRIPTION " "
::= { latinEventEntry 14 }

latinEventLifetime OBJECT-TYPE
    SYNTAX     Integer32 
    MAX-ACCESS read-create
    STATUS     current
    DESCRIPTION " "
::= { latinEventEntry 15 }

latinEventStorageType OBJECT-TYPE
    SYNTAX     StorageType 
    MAX-ACCESS read-create
    STATUS     current
    DESCRIPTION "Does nothing."
::= { latinEventEntry 16 }

latinEventStatus OBJECT-TYPE
    SYNTAX     RowStatus 
    MAX-ACCESS read-create
    STATUS     current
    DESCRIPTION "This is the row status for this table."
::= { latinEventEntry 17 }

latinEventSoftTrap OBJECT-TYPE
    SYNTAX     OCTET STRING
    MAX-ACCESS read-create
    STATUS     current
    DESCRIPTION "This object specifies a Soft Trap (as defined in the
                 SOFTTRAP-MIB) to be sent when an entry in the
                 latinEventTable is used to generate a trap.  If the value
                 of this object is a zero-length OctetString, then the
                 agent generates a latinEventTrap as specified elsewhere
                 in this MIB.  Otherwise, a Soft Trap is generated.  The
                 contents of this object must be either an ASCII string
                 specifying the textual name of the soft trap to be
                 generated, or an ASCII string representing an integer
                 value which specifies the index of the soft trap to
                 be generated.

                 The latinEventSoftTrapInstances object is used to
                 determine a set of instances to be used when generating
                 a soft trap."
::= { latinEventEntry 18 }

latinEventSoftTrapInstances OBJECT-TYPE
    SYNTAX     OCTET STRING
    MAX-ACCESS read-create
    STATUS     current
    DESCRIPTION "This object specifies a set of instances to be used
                 when generating a soft trap.  It must be an ASCII
                 string of the following format:

                     INST INST INST . . .

                 Each INST field (of which there may be zero, one, or more)
                 must each contain an OID fragment of the following form:

                     sid.sid.sid

                 Each sid is an integer value.  These instances will be
                 used as the instance list for generating the Soft Trap.
                 This list will be prefixed with the instances of the
                 entries in the following tables which are associated
                 with the trap:
                     - latinRecordHistoryTable
                     - latinFilterTable
                     - latinFilterHistoryTable
                     - latinEventTable
                     - latinLogTable

                 For example, if the string is '1.3 1.4', then
                 the generated Soft Trap  will use an instance list
                 which looks something like this:
                     1.7 1.1 1.5 1.1 1.1.5 1.3 1.4
                 The first five instances in the list mean that the
                 data was received on port 1, was placed
                 in the seventh entry in the latinRecordHistoryTable,
                 matched the first filter in the latinFilterTable, was
                 placed in the fifth entry in the latinFilterHistoryTable,
                 caused the first entry of the latinEventTable to be used
                 for generating events, and was logged in the fifth entry
                 in the latinLogTable."
::= { latinEventEntry 19 }

--
--
-- The latinLogTable.
--
--

latinLogTable OBJECT-TYPE
    SYNTAX     SEQUENCE OF LatinLogEntry
    MAX-ACCESS not-accessible
    STATUS     current
    DESCRIPTION "As an event, a LATIN agent can log the data records in an 
                 in-memory table.  The latinLogTable provides the in-memory
                 table."
::= { latinEvent 3 }

latinLogEntry OBJECT-TYPE
    SYNTAX     LatinLogEntry
    MAX-ACCESS not-accessible
    STATUS     current
    DESCRIPTION "Contains a single data record and its associated information."
    INDEX {latinPortIndex, latinEventIndex, latinLogIndex }
::= { latinLogTable 1 }

LatinLogEntry ::= SEQUENCE {
    latinLogIndex        Integer32,
    latinLogData         OctetString,
    latinLogTime         OctetString,
    latinLogTimeStamp    TimeStamp
}

latinLogIndex OBJECT-TYPE
    SYNTAX     Integer32 
    MAX-ACCESS not-accessible
    STATUS     current
    DESCRIPTION "Provides a unique numerical index for rows in this table."
::= { latinLogEntry 1 }

latinLogData OBJECT-TYPE
    SYNTAX     OCTET STRING
    MAX-ACCESS read-only
    STATUS     current
    DESCRIPTION "Contains the logged data record."
::= { latinLogEntry 2 }

latinLogTime OBJECT-TYPE
    SYNTAX     OCTET STRING
    MAX-ACCESS read-only
    STATUS     current
    DESCRIPTION "Specifies the time the incoming record arrived.  The LATIN 
                 agent records this time stamp in the format provided by the 
                 operating system under which the LATIN agent runs."
::= { latinLogEntry 3 }

latinLogTimeStamp OBJECT-TYPE
    SYNTAX     TimeStamp 
    MAX-ACCESS read-only
    STATUS     current
    DESCRIPTION "Specifies the time the incoming record arrived.  The LATIN 
                 agent records this time stamp in sysUpTime format."
::= { latinLogEntry 4 }


--
--
--  LATIN traps.
--
--

latinTraps OBJECT IDENTIFIER ::= { latin 5 }
 
latinMoreDataTrap NOTIFICATION-TYPE
    STATUS     current
    DESCRIPTION "When a LATIN agent receives new data records from a character
                 stream, it can send SNMP traps to alert an SNMP management
                 application.  This object defines the LATIN more data trap."
::= { latinTraps 1 }

latinEventTrap NOTIFICATION-TYPE
    STATUS     current
    DESCRIPTION "As an event, a LATIN agent can send traps to an SNMP
                 management application.  This object defines the event trap."
::= { latinTraps 2 }

latinPortNoCharsTrap NOTIFICATION-TYPE
    STATUS     current
    DESCRIPTION "The LATIN agent sends this trap if it does not receive
                 characters from the incoming datastream within the time
                 period specified by the latinPortNoCharsTrapPeriod.  This
                 helps a management application identify a possible 
                 failure of the character stream device."
::= { latinTraps 3 }

latinPortModemStatusChangeTrap NOTIFICATION-TYPE
    STATUS     current
    DESCRIPTION "The LATIN agent sends this trap if the modem status input
                 signals change.  This helps a management application 
                 identify a possible failure of the character stream device."
::= { latinTraps 4 }


END

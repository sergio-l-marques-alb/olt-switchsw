--
--
-- Copyright (C) 2004-2006 by SNMP Research, Incorporated.
--
-- This software is furnished under a license and may be used and copied
-- only in accordance with the terms of such license and with the
-- inclusion of the above copyright notice. This software or any other
-- copies thereof may not be provided or otherwise made available to any
-- other person. No title to and ownership of the software is hereby
-- transferred.
--
-- The information in this software is subject to change without notice
-- and should not be construed as a commitment by SNMP Research, Incorporated.
--
-- Restricted Rights Legend:
--  Use, duplication, or disclosure by the Government is subject to
--  restrictions as set forth in subparagraph (c)(1)(ii) of the Rights
--  in Technical Data and Computer Software clause at DFARS 252.227-7013;
--  subparagraphs (c)(4) and (d) of the Commercial Computer
--  Software-Restricted Rights Clause, FAR 52.227-19; and in similar
--  clauses in the NASA FAR Supplement and other corresponding
--  governmental regulations.
--
--

--
--                PROPRIETARY NOTICE
--
-- This software is an unpublished work subject to a confidentiality agreement
-- and is protected by copyright and trade secret law.  Unauthorized copying,
-- redistribution or other use of this work is prohibited.
--
-- The above notice of copyright on this source code product does not indicate
-- any actual or intended publication of such source code.
--

-- SNMP Advanced Protocol Operations (APO) Consortium MIB

APO-CONSORTIUM-MIB DEFINITIONS ::= BEGIN

IMPORTS
   MODULE-IDENTITY, enterprises
      FROM SNMPv2-SMI;

--
-- Top level assignment for the APO Consortium
--
apoConsortium MODULE-IDENTITY
    LAST-UPDATED "200410150000Z"
    ORGANIZATION "APO Consortium"
    CONTACT-INFO "Postal:  SNMP Research
                           3001 Kimberlin Heights Rd.
                           Knoxville, TN 37920-9716
                           USA
 
                  Tel:     +1 865 573 1434
                  E-mail:  info@snmp.com"
    DESCRIPTION  "Top level assigment for the APO Consortium"
    ::= { enterprises 21734 } --  IANA assigned


--
-- OID assignments for APO MIB modules
--
apoModules OBJECT IDENTIFIER ::= { apoConsortium 1 }

  apoCapabilitiesMIB     OBJECT IDENTIFIER ::= { apoModules 1 }
  apoAggregateMIB        OBJECT IDENTIFIER ::= { apoModules 2 }
  apoTargetParamsMIB     OBJECT IDENTIFIER ::= { apoModules 3 }

--
-- OID assigments for APO error codes
--
apoErrorCodes          OBJECT IDENTIFIER ::= { apoConsortium 2 }

  apoNoError             OBJECT IDENTIFIER ::= { apoErrorCodes 0 }
  apoTooBig              OBJECT IDENTIFIER ::= { apoErrorCodes 1 }
  apoNoSuchName          OBJECT IDENTIFIER ::= { apoErrorCodes 2 }
  apoBadValue            OBJECT IDENTIFIER ::= { apoErrorCodes 3 }
  apoReadOnly            OBJECT IDENTIFIER ::= { apoErrorCodes 4 }
  apoGenErr              OBJECT IDENTIFIER ::= { apoErrorCodes 5 }
  apoNoAccess            OBJECT IDENTIFIER ::= { apoErrorCodes 6 }
  apoWrongType           OBJECT IDENTIFIER ::= { apoErrorCodes 7 }
  apoWrongLength         OBJECT IDENTIFIER ::= { apoErrorCodes 8 }
  apoWrongEncoding       OBJECT IDENTIFIER ::= { apoErrorCodes 9 }
  apoWrongValue          OBJECT IDENTIFIER ::= { apoErrorCodes 10 }
  apoNoCreation          OBJECT IDENTIFIER ::= { apoErrorCodes 11 }
  apoInconsistentValue   OBJECT IDENTIFIER ::= { apoErrorCodes 12 }
  apoRapourceUnavailable OBJECT IDENTIFIER ::= { apoErrorCodes 13 }
  apoCommitFailed        OBJECT IDENTIFIER ::= { apoErrorCodes 14 }
  apoUndoFailed          OBJECT IDENTIFIER ::= { apoErrorCodes 15 }
  apoAuthorizationError  OBJECT IDENTIFIER ::= { apoErrorCodes 16 }
  apoNotWritable         OBJECT IDENTIFIER ::= { apoErrorCodes 17 }
  apoInconsistentName    OBJECT IDENTIFIER ::= { apoErrorCodes 18 }


END
